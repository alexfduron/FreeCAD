#Diseño parametrico de una Caja


'''
##############################################################################
#'                                                                          '#
#'                                                                          '#
#'   Copyright (c) 2026                                                     '#
#'   Original code by:                                                      '#
#'                       :::====   :::=====  :::====                        '#
#'                       :::  ===  :::       :::  ===                       '#
#'                       ========  ======    ===  ===                       '#
#'                       ===  ===  ===       ===  ===                       '#
#'                       ===  ===  ===       =======                        '#
#'                                                                          '#
#'   This program is free software, you can redistribute it and/or modify   '#
#'   it under the terms of the GNU Lesser General Public Licence ( LGPL )   '#
#'   as published by the Free Software Fundation;  either  version  2  of   '#
#'   the Licence, or (at your option) any later version.                    '#
#'   for detail see the LICENCE text file.                                  '#
#'                                                                          '#
#'   Use at your own risk. The author assumes no liability for data loss.   '#
#'              It is advised to backup your data frequently.               '#
#'             If you do not trust the software do not use it.              '#
#'                                                                          '#
#'   This software is distributed in the hope that  it  will  be  useful,   '#
#'   but WITHOUT ANY WARRANTY,  without  even  the  implied  warranty  of   '#
#'   MERCHANTABILITY  or  FITNESS  FOR  A  PARTICULAR  PURPOSE.  See  the   '#
#'   GNU Library General Public Licence for more details.                   '#
#'                                                                          '#
#'   You should have received a copy of the GNU  Library  General  Public   '#
#'   Licence along with this macro,  if not, write to the  Free  Software   '#
#'   Foundation Inc., 59 Temple Place, Suite 330,  Boston,  MA 02111-1307   '#
#'   USA.                                                                   '#
#'                                                                          '#
#'                                                                          '#
##############################################################################
'''

__Title__    = "FC_Bastidor"
__Author__   = "AFD"
__Version__  = "1.1.0"
__Date__     = "2026/03/29" #YYYY/MMM/DD

__Comment__  = "Esta macro crea un Bastidor para bordar en cintas"
__Web__      = "https://www.fastframes.com/product-page/nametape-hoops"
__Help__     = "inicia la Macro y sigue las instrucciones"
__Status__   = "estable"
__Requires__ = "freecad 1.1.0 and higher"


# importamos la libreria de "FreeCAD"
import FreeCAD as App
# importamo las librerias de "FreeCADGui" y "PySide" para limpiar la consola de python y la vista de informe
import FreeCADGui as Gui
from PySide import QtGui
# importamos la libreria de "PartDesign"
import PartDesign
# importamos la libreria de "Sketcher"
import Sketcher

# importamos la libreria de "math" para las funciones trigonometricas
import math
# importamos la libreria de "pandas" para el manejo de listas y tablas
import pandas as pd
# importamos la libreria de "datetime" para los nombres de la semana
import datetime
# importamos la libreria "time" para obtener la hora del sistema
import time



def Imprimir_Lista(Lista_X, Nom_Lista = 'Lista X'):
	
	# Aqui ajustamos las opciones de Pandas
	pd.set_option('display.max_columns', None)
	pd.set_option('display.max_rows', None)
	pd.set_option('display.width', 150)
	df = pd.DataFrame(Lista_X)
	
	# Aqui modificamos la apariencia de los datos
	df[1] = df[1].apply(lambda x : str(round(x, 3)).rstrip('0').rstrip('.'))
	df[2] = df[2].apply(lambda x : [ str(float(round(n, 3))).rstrip('0').rstrip('.').center(3) for n in x ])
	df[3] = df[3].apply(lambda x : [ str(float(round(n, 3))).rstrip('0').rstrip('.').center(3) for n in x ])
	df[4] = df[4].apply(lambda x : [ str(float(round(n, 3))).rstrip('0').rstrip('.').center(3) for n in x ])
	
	# Aqui agregamos los encabezados de las columnas
	newRow = pd.DataFrame(["ID obj", "Largo/Radio", "Punto inicio", "Punto final", "Punto centro", "Objeto", "Contenedor", "Grupo"]).T
	#df = df.set_axis(newRow.values[0], axis = "columns")
	df = pd.concat([df[:0], newRow.rename(columns=dict(zip(newRow.columns, df.columns))), df[0:]]).reset_index(drop = True)
	
	df = df.add_prefix("--", axis = "index")
	df = df.add_suffix("--", axis = "index")
	
	# Aqui mostramos la tabla en la consola de FreeCAD
	print(f'{Nom_Lista} = {len(Lista_X)}')
	print(df)
	print()
	
	
	
def Imprimir_Lista2(Lista_X, Nom_Lista = 'Lista X'):
	
	# Aqui ajustamos las opciones de Pandas
	pd.set_option('display.max_columns', None)
	pd.set_option('display.max_rows', None)
	pd.set_option('display.width', 150)
	df = pd.DataFrame(Lista_X)
	
	# Aqui modificamos la apariencia de los datos
	df[3] = df[3].apply(lambda x : str(round(x, 3)).rstrip('0').rstrip('.'))
	
	# Aqui agregamos los encabezados de las columnas
	newRow = pd.DataFrame(["ID restr", "Tipo", "Nombre", "Largo/Radio", "Grupo", "Contenedor", "Formula"]).T
	#df = df.set_axis(newRow.values[0], axis = "columns")
	df = pd.concat([df[:0], newRow.rename(columns=dict(zip(newRow.columns, df.columns))), df[0:]]).reset_index(drop = True)
	
	df = df.add_prefix("--", axis = "index")
	df = df.add_suffix("--", axis = "index")
	
	# Aqui mostramos la tabla en la consola de FreeCAD
	print(f'{Nom_Lista} = {len(Lista_X)}')
	print(df)
	print()
	
	
	
def Limpiar_Pantalla():
	
	mw = Gui.getMainWindow()
	
	rv = mw.findChild(QtGui.QTextEdit, "Report view")
	rv.clear()
	
	pc = mw.findChild(QtGui.QPlainTextEdit,"Python console")
	pc.onClearConsole()
	
	

#! Estas son las funciones para las partes que forman el Bastidor
def Crear_Hoop2(Largo_Total, Ancho_Total, Alto_Total):
	
	# aqui convertimos el texto a numero con las unidades por defecto en FreeCAD
	try:
		LaT = App.Units.Quantity(Largo_Total).Value
	except:
		raise TypeError(f'\n\n\t Mensaje = No es Numero \n\t Funcion = Crear_Bastidor \n\t (Largo_Total) = "{Largo_Total}"  ==>  {type(Largo_Total)}')
	
	try:
		AnT = App.Units.Quantity(Ancho_Total).Value
	except:
		raise TypeError(f'\n\n\t Mensaje = No es Numero \n\t Funcion = Crear_Bastidor \n\t (Ancho_Total) = "{Ancho_Total}"  ==>  {type(Ancho_Total)}')
	try:
		AlT = App.Units.Quantity(Alto_Total).Value
	except:
		raise TypeError(f'\n\n\t Mensaje = No es Numero \n\t Funcion = Crear_Bastidor \n\t (Alto_Total) = "{Alto_Total}"  ==>  {type(Alto_Total)}')
	
	# Limpiar_Pantalla():
	Limpiar_Pantalla()
	
	# Crear_Contenedor_3D(LaT, AnT, AlT):
	Crear_Contenedor_3D(LaT, AnT, AlT)
	
	# Crear_Bastidor_3D():
	Crear_Bastidor_3D()
	
	# Crear_Huecos01_3D(LaT, AnT, AlT):
	Crear_Huecos01_3D(LaT, AnT, AlT)
	
	# Crear_Huecos02_3D(LaT, AnT, AlT):
	Crear_Huecos02_3D(LaT, AnT, AlT)
	'''
	# Crear_Huecos03_3D(LaT, AnT, AlT):
	Crear_Huecos03_3D(LaT, AnT, AlT)
	
	# Crear_Doblez01():
	Crear_Doblez01()
	Crear_Doblez02()
	Crear_Doblez03()
	Crear_Doblez04()
	Crear_Doblez05()
	Crear_Doblez06()
	Crear_Doblez07()
	Crear_Doblez08()
	
	# Crear_Huecos04_3D(LaT, AnT, AlT):
	Crear_Huecos04_3D(LaT, AnT, AlT)
	
	# Crear_Huecos05_3D(LaT, AnT, AlT):
	Crear_Huecos05_3D(LaT, AnT, AlT)
	
	# Crear_Relleno01_3D(LaT, AnT, AlT):
	Crear_Relleno01_3D(LaT, AnT, AlT)
	
	# Crear_Relleno02_3D(LaT, AnT, AlT):
	Crear_Relleno02_3D(LaT, AnT, AlT)
	'''
	
	
	
	
	
	
	
	
	
	
	
	
	
	
	
	
	
	
	
	
#! Crea el contenedor del objeto 3D
def Crear_Contenedor_3D(LaT, AnT, AlT):
	
	### iniciar la orden Std_Part
	global Pieza_B1
	Pieza_B1 = Crear_Pieza('P001', 'Pieza_B001')
	
	global Variable_B1
	### iniciar la orden Var_Set
	Variable_B1 = Crear_Variables('VarSet_B001', 'Variables_B001', Pieza_B1, LaT, AnT, AlT)
	
	### iniciar la orden PartDesign_Body
	global Cuerpo_B1
	Cuerpo_B1 = Crear_Cuerpo('Body_B001', 'Cuerpo_B001', Pieza_B1)
	
	
	
def Crear_Pieza(Titulo, Etiqueta = ''):
	
	Crear_Doc()
	Pieza_X = Doc.addObject('App::Part', Titulo)
	Doc.Tip = Pieza_X
	if Etiqueta == '':
		Pieza_X.Label = Titulo
	else:
		Pieza_X.Label = Etiqueta
		
	Doc.recompute()
	return Pieza_X
	


def Crear_Doc():
	
	# Tomamos el archivo activo
	global Doc
	Doc = App.activeDocument()
	
	

def Crear_Variables(Titulo, Etiqueta, Objeto_X, LaT, AnT, AlT):
	
	# creamos las variables del objeto
	Var_X = Doc.addObject("App::VarSet", Titulo)
	Var_X.Label = Etiqueta
	Objeto_X.addObject(Var_X)
	
	Var_X.addProperty("App::PropertyLength", "Largo",     group="Grupo_Bastidor",    doc="Esta propiedad modifica el Largo del Bastidor")
	Var_X.Largo = LaT
	Var_X.addProperty("App::PropertyLength", "Ancho",     group="Grupo_Bastidor",    doc="Esta propiedad modifica el Ancho del Bastidor")
	Var_X.Ancho = AnT
	Var_X.addProperty("App::PropertyLength", "Alto",      group="Grupo_Bastidor",    doc="Esta propiedad modifica el Alto del Bastidor")
	Var_X.Alto = AlT
	Var_X.addProperty("App::PropertyLength", "Espesor",   group="Grupo_Bastidor",    doc="Esta propiedad modifica el grosor del Bastidor")
	Var_X.Espesor = "2 mm"
	
	Doc.recompute()
	return Var_X
	
	
	
def Crear_Cuerpo(Titulo, Etiqueta = '', Objeto_X = False):
	
	Cuerpo_X = Doc.addObject('PartDesign::Body', Titulo)
	if Etiqueta == '':
		Cuerpo_X.Label = Titulo
	else:
		Cuerpo_X.Label = Etiqueta
	if Objeto_X == False:
		Doc.Tip = Cuerpo_X
	else:
		Objeto_X.addObject(Cuerpo_X)
		
	Doc.recompute()
	return Cuerpo_X
	
	
	
def Crear_Boceto(Titulo, Etiqueta = '', Objeto_X = False, Plano_X = '', Modelado_X = '', Mapa_X = 'FlatFace'):
	
	Boceto_X = Doc.addObject('Sketcher::SketchObject', Titulo)
	Doc.Tip = Boceto_X
	if Etiqueta == '':
		Boceto_X.Label = Titulo
	else:
		Boceto_X.Label = Etiqueta
	Boceto_X.MapMode = Mapa_X
	if Modelado_X == '':
		if Plano_X == '':
			Plano_X = 'XY_Plane'
		if Objeto_X == False:
			Doc.Tip = Boceto_X
			Cuerpo_New = Crear_Cuerpo('New_Body', '', Pieza_C1)
			Cuerpo_New.addObject(Boceto_X)
			for k in Cuerpo_New.Origin.OriginFeatures:
				if k.Role == Plano_X:
					XY_Plano = k
			Boceto_X.AttachmentSupport = (Cuerpo_New.Origin, [XY_Plano.Name])
			del XY_Plano
		else:
			Objeto_X.addObject(Boceto_X)
			for k in Objeto_X.Origin.OriginFeatures:
				if k.Role == Plano_X:
					XY_Plano = k
			Boceto_X.AttachmentSupport = (Objeto_X.Origin, [XY_Plano.Name])
			del XY_Plano
	else:
		Objeto_X.addObject(Boceto_X)
		Boceto_X.AttachmentSupport = (Modelado_X, [Plano_X])
		
	Doc.recompute()
	return Boceto_X
	
	
	
def Crear_LineaRef(Titulo, Etiqueta = '', Objeto_X = False, Eje_X = '', Modelado_X = ''):
	
	LinRef_X = Doc.addObject('Part::DatumLine', Titulo)
	if Etiqueta == '':
		LinRef_X.Label = Titulo
	else:
		LinRef_X.Label = Etiqueta
	if Objeto_X == False:
		Doc.Tip = LinRef_X
	else:
		Objeto_X.addObject(LinRef_X)
	LinRef_X.MapMode = 'TwoPointLine'
	LinRef_X.AttachmentSupport = [(Modelado_X, Eje_X)]
	
	Doc.recompute()
	return LinRef_X
	
	
	
def Crear_PlanoRef(Titulo, Etiqueta = '', Objeto_X = False, Eje_X = '', Modelado_X = ''):
	
	PlanRef_X = Doc.addObject('Part::DatumPlane', Titulo)
	if Etiqueta == '':
		PlanRef_X.Label = Titulo
	else:
		PlanRef_X.Label = Etiqueta
	if Objeto_X == False:
		Doc.Tip = PlanRef_X
	else:
		Objeto_X.addObject(PlanRef_X)
	PlanRef_X.MapMode = 'NormalToEdge'
	PlanRef_X.AttachmentSupport = [(Modelado_X, Eje_X)]
	
	Doc.recompute()
	return PlanRef_X
	
	
	
#! Estos son las funciones para crear Objetos 2D
def Crear_Linea(Pt1, Pt2, Boceto_X, Guia = False, Grupo_X = '-'):
	
	# aqui guardamos el ID de la linea.
	Lista_Obj.append(list(Boceto_X.addGeometry([Part.LineSegment(Pt1, Pt2)], Guia)))
	# aqui redondeamos los valores numericos de los vectores
	Pt1_Temp = [round(Pt1[0], 8), round(Pt1[1], 8), round(Pt1[2], 8)]
	Pt2_Temp = [round(Pt2[0], 8), round(Pt2[1], 8), round(Pt2[2], 8)]
	# aqui guardamos la magnitud de la linea.
	Pt3 = App.Vector(Pt2) - App.Vector(Pt1)
	Lista_Obj[-1].append(round(Pt3.Length, 8))
	# aqui guardamos el punto inicial.
	Lista_Obj[-1].append(Pt1_Temp)
	# aqui guardamos el punto final.
	Lista_Obj[-1].append(Pt2_Temp)
	# aqui guardamos el punto centro => N/A.
	Lista_Obj[-1].append([0.0, 0.0, 0.0])
	# aqui guardamos el nombre del objeto.
	Lista_Obj[-1].append('linea')
	# aqui guardamos el Boceto que contiene la linea.
	Lista_Obj[-1].append(Boceto_X.Label)
	# aqui guardamos el Grupo que contiene la linea.
	Lista_Obj[-1].append(Grupo_X)
	
	
	
def Crear_Arco(Pt1, Eje, Radio, Boceto_X, Ang_Ini, Ang_Fin, Guia = False, Grupo_X = '-'):
	
	# aqui guardamos el ID del arco.
	Lista_Obj.append(list(Boceto_X.addGeometry([Part.ArcOfCircle(Part.Circle(Pt1, Eje , Radio), Ang_Ini, Ang_Fin)], Guia)))
	# aqui creamos los puntos de los extremos del arco con los valores numericos redondeados
	Pt1_Temp = App.Vector(round(Pt1.x + Radio * math.cos(Ang_Ini), 8), round(Pt1.y + Radio * math.sin(Ang_Ini), 8), round(Pt1.z, 8))
	Pt2_Temp = App.Vector(round(Pt1.x + Radio * math.cos(Ang_Fin), 8), round(Pt1.y + Radio * math.sin(Ang_Fin), 8), round(Pt1.z, 8))
	Eje_Temp = App.Vector(round(Pt1.x, 8), round(Pt1.y, 8), round(Pt1.z, 8))
	# aqui guardamos el radio.
	Lista_Obj[-1].append(round(Radio, 8))
	# aqui guardamos el punto inicial.
	Lista_Obj[-1].append(list(Pt1_Temp))
	# aqui guardamos el punto final.
	Lista_Obj[-1].append(list(Pt2_Temp))
	# aqui guardamos el punto central del arco.
	Lista_Obj[-1].append(list(Eje_Temp))
	# aqui guardamos el nombre del objeto.
	Lista_Obj[-1].append('arco')
	# aqui guardamos el Boceto que contiene al arco.
	Lista_Obj[-1].append(Boceto_X.Label)
	# aqui guardamos el Grupo que contiene al arco.
	Lista_Obj[-1].append(Grupo_X)
	
	
	
def Crear_Circulo(Pt1, Eje, Radio, Boceto_X, Guia = False, Grupo_X = '-'):
	
	# aqui guardamos el ID del circulo.
	Lista_Obj.append(list(Boceto_X.addGeometry([Part.Circle(Pt1, Eje, Radio)], Guia)))
	# aqui creamos el punto centro del circulo con los valores numericos redondeados
	Eje_Temp = App.Vector(round(Pt1.x, 8), round(Pt1.y, 8), round(Pt1.z, 8))
	# aqui guardamos el radio.
	Lista_Obj[-1].append(round(Radio, 8))
	# aqui guardamos el punto inicial => N/A.
	Lista_Obj[-1].append([0, 0, 0])
	# aqui guardamos el punto final => N/A.
	Lista_Obj[-1].append([0, 0, 0])
	# aqui guardamos el punto central del circulo.
	Lista_Obj[-1].append(list(Eje_Temp))
	# aqui guardamos el nombre del objeto.
	Lista_Obj[-1].append('circulo')
	# aqui guardamos el Boceto que contiene al circulo.
	Lista_Obj[-1].append(Boceto_X.Label)
	# aqui guardamos el Grupo que contiene al circulo.
	Lista_Obj[-1].append(Grupo_X)
	
	
	
def Crear_Punto(Pt1, Boceto_X, Guia = False, Grupo_X = '-'):
	
	# aqui guardamos el ID del punto.
	Lista_Obj.append(list(Boceto_X.addGeometry([Part.Point(Pt1)], Guia)))
	# aqui redondeamos los valores numericos de los vectores
	Pt1_Temp = [round(Pt1[0], 8), round(Pt1[1], 8), round(Pt1[2], 8)]
	# aqui guardamos la magnitud del punto => N/A.
	Lista_Obj[-1].append(0)
	# aqui guardamos el punto inicial.
	Lista_Obj[-1].append(Pt1_Temp)
	# aqui guardamos el punto final => N/A.
	Lista_Obj[-1].append([0.0, 0.0, 0.0])
	# aqui guardamos el punto centro => N/A.
	Lista_Obj[-1].append([0.0, 0.0, 0.0])
	# aqui guardamos el nombre del objeto.
	Lista_Obj[-1].append('punto')
	# aqui guardamos el Boceto que contiene el punto.
	Lista_Obj[-1].append(Boceto_X.Label)
	# aqui guardamos el Grupo que contiene el punto.
	Lista_Obj[-1].append(Grupo_X)
	
	
	
def Crear_Cuadrado(Pt1, Boceto_X, Tipo = 'Borde', Dist_X = False, Dist_Y = False, Radio = False, Angulo = 0, Guia = False, Grupo = '-'):
	
	# Tipos:
	#	Esquina
	#	Borde
	
	# validar entrada
	if Dist_X == False:
		Dist_X = 100
	else:
		Dist_X = Dist_X / 2
	if Dist_Y == False:
		Dist_Y = 100
	else:
		Dist_Y = Dist_Y / 2
	if Radio == False:
		Radio = 10
	
	lastID = len(Boceto_X.Geometry)
	
	# creamos la lista de puntos por cada linea
	geoList = []
	if Tipo == 'Borde':
		# [Punto inicial, Punto final]
		geoList.append([App.Vector(-Dist_X + Pt1.x,          Dist_Y - Radio + Pt1.y, Pt1.z), App.Vector(-Dist_X + Pt1.x,         -Dist_Y + Radio + Pt1.y, Pt1.z)])		#Object[B0]
		geoList.append([App.Vector(-Dist_X + Radio + Pt1.x, -Dist_Y + Pt1.y,         Pt1.z), App.Vector( Dist_X - Radio + Pt1.x, -Dist_Y + Pt1.y,         Pt1.z)])		#Object[B1]
		geoList.append([App.Vector( Dist_X + Pt1.x,         -Dist_Y + Radio + Pt1.y, Pt1.z), App.Vector( Dist_X + Pt1.x,          Dist_Y - Radio + Pt1.y, Pt1.z)])		#Object[B2]
		geoList.append([App.Vector( Dist_X - Radio +Pt1.x,   Dist_Y + Pt1.y,         Pt1.z), App.Vector(-Dist_X + Radio + Pt1.x,  Dist_Y + Pt1.y,         Pt1.z)])		#Object[B3]
	
	if Tipo == 'Esquina':
		# [Punto inicial, Punto final]
		geoList.append([App.Vector(-Dist_X + Pt1.x,  Dist_Y + Pt1.y, Pt1.z), App.Vector(-Dist_X + Pt1.x, -Dist_Y + Pt1.y, Pt1.z)])		#Object[E0]
		geoList.append([App.Vector(-Dist_X + Pt1.x, -Dist_Y + Pt1.y, Pt1.z), App.Vector( Dist_X + Pt1.x, -Dist_Y + Pt1.y, Pt1.z)])		#Object[E1]
		geoList.append([App.Vector( Dist_X + Pt1.x, -Dist_Y + Pt1.y, Pt1.z), App.Vector( Dist_X + Pt1.x,  Dist_Y + Pt1.y, Pt1.z)])		#Object[E2]
		geoList.append([App.Vector( Dist_X + Pt1.x,  Dist_Y + Pt1.y, Pt1.z), App.Vector(-Dist_X + Pt1.x,  Dist_Y + Pt1.y, Pt1.z)])		#Object[E3]
	
	for NewLinea in geoList:
		if Guia == False:
			# Crear_Linea(Pt1, Pt2, Boceto_X, Guia = False, Grupo_X = '-'):
			Crear_Linea(NewLinea[0], NewLinea[1], Boceto_X, Guia, Grupo)
		else:
			# Crear_Linea(Pt1, Pt2, Boceto_X, Guia = False, Grupo_X = '-'):
			Crear_Linea(NewLinea[0], NewLinea[1], Boceto_X, Guia, Grupo + '_G')
	
	del geoList
	
	if Tipo == 'Borde':
		# creamos la lista de puntos por cada arco
		geoList = []
		# [centro curva, Eje, Radio, Angulo inicial, Angulo final]
		geoList.append([App.Vector(-Dist_X + Radio + Pt1.x,  Dist_Y - Radio + Pt1.y, Pt1.z), App.Vector(0, 0, 1), Radio, math.radians( 90), math.radians(180)])	#Object[B4]
		geoList.append([App.Vector(-Dist_X + Radio + Pt1.x, -Dist_Y + Radio + Pt1.y, Pt1.z), App.Vector(0, 0, 1), Radio, math.radians(180), math.radians(270)])	#Object[B5]
		geoList.append([App.Vector( Dist_X - Radio + Pt1.x, -Dist_Y + Radio + Pt1.y, Pt1.z), App.Vector(0, 0, 1), Radio, math.radians(270), math.radians(360)])	#Object[B6]
		geoList.append([App.Vector( Dist_X - Radio + Pt1.x,  Dist_Y - Radio + Pt1.y, Pt1.z), App.Vector(0, 0, 1), Radio, math.radians(  0), math.radians( 90)])	#Object[B7]
		
		for NewArco in geoList:
			if Guia == False:
				# Crear_Arco(Pt1, Eje, Radio, Boceto_X, Ang_Ini, Ang_Fin, Guia = False, Grupo_X = '-'):
				Crear_Arco(NewArco[0], NewArco[1], NewArco[2], Boceto_X, NewArco[3], NewArco[4], Guia, Grupo)
			else:
				# Crear_Arco(Pt1, Eje, Radio, Boceto_X, Ang_Ini, Ang_Fin, Guia = False, Grupo_X = '-'):
				Crear_Arco(NewArco[0], NewArco[1], NewArco[2], Boceto_X, NewArco[3], NewArco[4], Guia, Grupo + '_G')
		
		del geoList
	
	# creamos la lista de puntos auxiliares
	geoList = []
	if Tipo == 'Borde':
		# [Punto inicial]
		geoList.append([App.Vector(-Dist_X + Pt1.x,  Dist_Y + Pt1.y, Pt1.z)])		#Object[B8]
		geoList.append([App.Vector( Dist_X + Pt1.x,  Dist_Y + Pt1.y, Pt1.z)])		#Object[B9]
		geoList.append([App.Vector( Dist_X + Pt1.x, -Dist_Y + Pt1.y, Pt1.z)])		#Object[B10]
		geoList.append([App.Vector(-Dist_X + Pt1.x, -Dist_Y + Pt1.y, Pt1.z)])		#Object[B11]
	# [Punto inicial]
	geoList.append([App.Vector(Pt1.x, Pt1.y, Pt1.z)])							#Object[B12,E4]
	
	for NewPunto in geoList:
		# Crear_Punto(Pt1, Boceto_X, Guia = False, Grupo_X = '-'):
		Crear_Punto(NewPunto[0], Boceto_X, True, Grupo + '_G')
		
	del geoList
	
	# creamos la lista de puntos por cada linea auxiliar
	geoList = []
	# [Punto inicial, Punto final]
	geoList.append([App.Vector(Pt1.x, Pt1.y, Pt1.z), App.Vector(Radio + Pt1.x, Pt1.y, Pt1.z)])		#Object[B13,E5]
	geoList.append([App.Vector(Pt1.x, Pt1.y, Pt1.z), App.Vector(Radio + Pt1.x, Pt1.y, Pt1.z)])		#Object[B14,E6]
	
	for NewLinea in geoList:
		# Crear_Linea(Pt1, Pt2, Boceto_X, Guia = False, Grupo_X = '-'):
		Crear_Linea(NewLinea[0], NewLinea[1], Boceto_X, True, Grupo + '_G')
	
	del geoList
	
	# creamos la lista de restricciones
	constraintList = []
	if Tipo == 'Borde':
		constraintList.append(Sketcher.Constraint('Tangent',       lastID + 0,1,  lastID + 4,2))					#Constraints[0]
		constraintList.append(Sketcher.Constraint('Tangent',       lastID + 0,2,  lastID + 5,1))					#Constraints[1]
		constraintList.append(Sketcher.Constraint('Tangent',       lastID + 1,1,  lastID + 5,2))					#Constraints[2]
		constraintList.append(Sketcher.Constraint('Tangent',       lastID + 1,2,  lastID + 6,1))					#Constraints[3]
		constraintList.append(Sketcher.Constraint('Tangent',       lastID + 2,1,  lastID + 6,2))					#Constraints[4]
		constraintList.append(Sketcher.Constraint('Tangent',       lastID + 2,2,  lastID + 7,1))					#Constraints[5]
		constraintList.append(Sketcher.Constraint('Tangent',       lastID + 3,1,  lastID + 7,2))					#Constraints[6]
		constraintList.append(Sketcher.Constraint('Tangent',       lastID + 3,2,  lastID + 4,1))					#Constraints[7]
		constraintList.append(Sketcher.Constraint('Perpendicular', lastID + 0,    lastID + 1))					#Constraints[8]
		constraintList.append(Sketcher.Constraint('Perpendicular', lastID + 1,    lastID + 2))					#Constraints[9]
		constraintList.append(Sketcher.Constraint('Perpendicular', lastID + 2,    lastID + 3))					#Constraints[10]
		constraintList.append(Sketcher.Constraint('Equal',         lastID + 4,    lastID + 5))					#Constraints[11]
		constraintList.append(Sketcher.Constraint('Equal',         lastID + 5,    lastID + 6))					#Constraints[12]
		constraintList.append(Sketcher.Constraint('Equal',         lastID + 6,    lastID + 7))					#Constraints[13]
		constraintList.append(Sketcher.Constraint('PointOnObject', lastID + 8,1,  lastID + 0))					#Constraints[14]
		constraintList.append(Sketcher.Constraint('PointOnObject', lastID + 8,1,  lastID + 3))					#Constraints[15]
		constraintList.append(Sketcher.Constraint('PointOnObject', lastID + 9,1,  lastID + 2))					#Constraints[16]
		constraintList.append(Sketcher.Constraint('PointOnObject', lastID + 9,1,  lastID + 3))					#Constraints[17]
		constraintList.append(Sketcher.Constraint('PointOnObject', lastID + 10,1, lastID + 1))					#Constraints[18]
		constraintList.append(Sketcher.Constraint('PointOnObject', lastID + 10,1, lastID + 2))					#Constraints[19]
		constraintList.append(Sketcher.Constraint('PointOnObject', lastID + 11,1, lastID + 0))					#Constraints[20]
		constraintList.append(Sketcher.Constraint('PointOnObject', lastID + 11,1, lastID + 1))					#Constraints[21]
		constraintList.append(Sketcher.Constraint('Radius',        lastID + 5,    Radio)) 						#Constraints[22]
		constraintList.append(Sketcher.Constraint('Distance',      lastID + 8,1,  lastID + 9,1,  2*Dist_X))		#Constraints[23]
		constraintList.append(Sketcher.Constraint('Distance',      lastID + 9,1,  lastID + 10,1, 2*Dist_Y))		#Constraints[24]
		constraintList.append(Sketcher.Constraint('Symmetric',     lastID + 8,1,  lastID + 10,1, lastID + 12,1))	#Constraints[25]
		constraintList.append(Sketcher.Constraint('Coincident',    lastID + 13,1, lastID + 12,1))					#Constraints[26]
		constraintList.append(Sketcher.Constraint('Parallel',      lastID + 13,   lastID + 3))					#Constraints[27]
		constraintList.append(Sketcher.Constraint('Distance',      lastID + 13,1, lastID + 13,2, Radio))			#Constraints[28]
		constraintList.append(Sketcher.Constraint('Coincident',    lastID + 14,1, lastID + 12,1))					#Constraints[29]
		constraintList.append(Sketcher.Constraint('Horizontal',    lastID + 14))									#Constraints[30]
		constraintList.append(Sketcher.Constraint('DistanceX',     lastID + 14,1, lastID + 14,2, Radio))			#Constraints[31]
		constraintList.append(Sketcher.Constraint('Angle',         lastID + 14,1, lastID + 13,1,  Angulo))		#Constraints[32]
		constraintList.append(Sketcher.Constraint('DistanceX',     lastID + 12,1, Pt1.x))							#Constraints[33]
		constraintList.append(Sketcher.Constraint('DistanceY',     lastID + 12,1, Pt1.y))							#Constraints[34]
	
	if Tipo == 'Esquina':
		constraintList.append(Sketcher.Constraint('Coincident',    lastID + 0,2, lastID + 1,1))					#Constraints[0]
		constraintList.append(Sketcher.Constraint('Coincident',    lastID + 1,2, lastID + 2,1))					#Constraints[1]
		constraintList.append(Sketcher.Constraint('Coincident',    lastID + 2,2, lastID + 3,1))					#Constraints[2]
		constraintList.append(Sketcher.Constraint('Coincident',    lastID + 3,2, lastID + 0,1))					#Constraints[3]
		constraintList.append(Sketcher.Constraint('Perpendicular', lastID + 0,   lastID + 1))						#Constraints[4]
		constraintList.append(Sketcher.Constraint('Perpendicular', lastID + 1,   lastID + 2))						#Constraints[5]
		constraintList.append(Sketcher.Constraint('Perpendicular', lastID + 2,   lastID + 3))						#Constraints[6]
		constraintList.append(Sketcher.Constraint('Distance',      lastID + 3,1, lastID + 3,2, 2*Dist_X))			#Constraints[7]
		constraintList.append(Sketcher.Constraint('Distance',      lastID + 0,1, lastID + 0,2, 2*Dist_Y))			#Constraints[8]
		constraintList.append(Sketcher.Constraint('Symmetric',     lastID + 0,1, lastID + 1,2, lastID + 4,1))		#Constraints[9]
		constraintList.append(Sketcher.Constraint('Coincident',    lastID + 5,1, lastID + 4,1))					#Constraints[10]
		constraintList.append(Sketcher.Constraint('Parallel',      lastID + 5,   lastID + 3))						#Constraints[11]
		constraintList.append(Sketcher.Constraint('Distance',      lastID + 5,1, lastID + 5,2, 10))				#Constraints[12]
		constraintList.append(Sketcher.Constraint('Coincident',    lastID + 6,1, lastID + 4,1))					#Constraints[13]
		constraintList.append(Sketcher.Constraint('Horizontal',    lastID + 6))									#Constraints[14]
		constraintList.append(Sketcher.Constraint('DistanceX',     lastID + 6,1, lastID + 6,2, 10))				#Constraints[15]
		constraintList.append(Sketcher.Constraint('Angle',         lastID + 6,1, lastID + 5,1, Angulo))			#Constraints[16]
		constraintList.append(Sketcher.Constraint('DistanceX',     lastID + 4,1, Pt1.x))							#Constraints[17]
		constraintList.append(Sketcher.Constraint('DistanceY',     lastID + 4,1, Pt1.y))							#Constraints[18]
		
	Boceto_X.addConstraint(constraintList)
	
	del constraintList
	
	Doc.recompute()
	
	
	
def Crear_Ranura(Pt1, Boceto_X, Dist_X = False, Dist_Y = False, Angulo = 0, Guia = False, Grupo = '-'):
	
	# validar entrada
	if Dist_X == False:
		Dist_X = 100
	else:
		Dist_X = Dist_X / 2
	if Dist_Y == False:
		Dist_Y = 50
	else:
		Dist_Y = Dist_Y / 2
	Radio = Dist_Y
	
	lastID = len(Boceto_X.Geometry)
	
	# creamos la lista de puntos por cada arco
	geoList = []
	# [centro curva, Eje, Radio, Angulo inicial, Angulo final]
	geoList.append([App.Vector(-Dist_X + Radio + Pt1.x, Pt1.y, Pt1.z), App.Vector(0, 0, 1), Radio, math.radians( 90), math.radians(180)])	#Object[0]
	geoList.append([App.Vector(-Dist_X + Radio + Pt1.x, Pt1.y, Pt1.z), App.Vector(0, 0, 1), Radio, math.radians(180), math.radians(270)])	#Object[1]
	geoList.append([App.Vector( Dist_X - Radio + Pt1.x, Pt1.y, Pt1.z), App.Vector(0, 0, 1), Radio, math.radians(270), math.radians(360)])	#Object[2]
	geoList.append([App.Vector( Dist_X - Radio + Pt1.x, Pt1.y, Pt1.z), App.Vector(0, 0, 1), Radio, math.radians(  0), math.radians( 90)])	#Object[3]
	
	for NewArco in geoList:
		if Guia == False:
			# Crear_Arco(Pt1, Eje, Radio, Boceto_X, Ang_Ini, Ang_Fin, Guia = False, Grupo_X = '-'):
			Crear_Arco(NewArco[0], NewArco[1], NewArco[2], Boceto_X, NewArco[3], NewArco[4], Guia, Grupo)
		else:
			# Crear_Arco(Pt1, Eje, Radio, Boceto_X, Ang_Ini, Ang_Fin, Guia = False, Grupo_X = '-'):
			Crear_Arco(NewArco[0], NewArco[1], NewArco[2], Boceto_X, NewArco[3], NewArco[4], Guia, Grupo + '_G')
	
	del geoList
	
	# creamos la lista de puntos por cada linea
	geoList = []
	# [Punto inicial, Punto final]
	geoList.append([App.Vector(-Dist_X + Radio + Pt1.x,  Dist_Y + Pt1.y, Pt1.z), App.Vector(Dist_X - Radio + Pt1.x,  Dist_Y + Pt1.y, Pt1.z)])		#Object[4]
	geoList.append([App.Vector(-Dist_X + Radio + Pt1.x, -Dist_Y + Pt1.y, Pt1.z), App.Vector(Dist_X - Radio + Pt1.x, -Dist_Y + Pt1.y, Pt1.z)])		#Object[5]
	
	for NewLinea in geoList:
		if Guia == False:
			# Crear_Linea(Pt1, Pt2, Boceto_X, Guia = False, Grupo_X = '-'):
			Crear_Linea(NewLinea[0], NewLinea[1], Boceto_X, Guia, Grupo)
		else:
			# Crear_Linea(Pt1, Pt2, Boceto_X, Guia = False, Grupo_X = '-'):
			Crear_Linea(NewLinea[0], NewLinea[1], Boceto_X, Guia, Grupo + '_G')
	
	del geoList
	
	# creamos la lista de puntos por cada linea auxiliar
	geoList = []
	# [Punto inicial, Punto final]
	geoList.append([App.Vector(-Dist_X + Pt1.x, Pt1.y, Pt1.z),         App.Vector(-Dist_X + Radio + Pt1.x, Pt1.y, Pt1.z)])				#Object[6]
	geoList.append([App.Vector(-Dist_X + Radio + Pt1.x, Pt1.y, Pt1.z), App.Vector(-Dist_X + Radio + Pt1.x, Dist_Y + Pt1.y, Pt1.z)])		#Object[7]
	geoList.append([App.Vector( Dist_X + Pt1.x, Pt1.y, Pt1.z),         App.Vector( Dist_X - Radio + Pt1.x, Pt1.y, Pt1.z)])				#Object[8]
	geoList.append([App.Vector( Dist_X - Radio + Pt1.x, Pt1.y, Pt1.z), App.Vector( Dist_X - Radio + Pt1.x, -Dist_Y + Pt1.y, Pt1.z)])		#Object[9]
	geoList.append([App.Vector(-Dist_X + Pt1.x,  Dist_Y + Pt1.y, Pt1.z), App.Vector(-Dist_X + Radio + Pt1.x,  Dist_Y + Pt1.y, Pt1.z)])	#Object[10]
	geoList.append([App.Vector( Dist_X + Pt1.x,  Dist_Y + Pt1.y, Pt1.z), App.Vector( Dist_X - Radio + Pt1.x,  Dist_Y + Pt1.y, Pt1.z)])	#Object[11]
	geoList.append([App.Vector(-Dist_X + Pt1.x, -Dist_Y + Pt1.y, Pt1.z), App.Vector(-Dist_X + Radio + Pt1.x, -Dist_Y + Pt1.y, Pt1.z)])	#Object[12]
	geoList.append([App.Vector( Dist_X + Pt1.x, -Dist_Y + Pt1.y, Pt1.z), App.Vector( Dist_X - Radio + Pt1.x, -Dist_Y + Pt1.y, Pt1.z)])	#Object[13]
	
	geoList.append([App.Vector( Pt1.x, Pt1.y, Pt1.z), App.Vector( Radio + Pt1.x, Pt1.y, Pt1.z)])			#Object[14]
	geoList.append([App.Vector( Pt1.x, Pt1.y, Pt1.z), App.Vector( Radio + Pt1.x, Pt1.y, Pt1.z)])			#Object[15]
	
	for NewLinea in geoList:
		# Crear_Linea(Pt1, Pt2, Boceto_X, Guia = False, Grupo_X = '-'):
		Crear_Linea(NewLinea[0], NewLinea[1], Boceto_X, True, Grupo + '_G')
	
	del geoList
	
	# creamos la lista de puntos auxiliares
	geoList = []
	# [Punto inicial]
	geoList.append([App.Vector(Pt1.x, Pt1.y, Pt1.z)])			#Object[16]
	
	for NewPunto in geoList:
		# Crear_Punto(Pt1, Boceto_X, Guia = False, Grupo_X = '-'):
		Crear_Punto(NewPunto[0], Boceto_X, True, Grupo + '_G')
		
	del geoList
	
	# creamos la lista de restricciones
	constraintList = []
	constraintList.append(Sketcher.Constraint('Tangent',       lastID + 0,1,  lastID + 4,1))						#Constraints[0]
	constraintList.append(Sketcher.Constraint('Tangent',       lastID + 0,2,  lastID + 1,1))						#Constraints[1]
	constraintList.append(Sketcher.Constraint('Tangent',       lastID + 1,2,  lastID + 5,1))						#Constraints[2]
	constraintList.append(Sketcher.Constraint('Tangent',       lastID + 2,1,  lastID + 5,2))						#Constraints[3]
	constraintList.append(Sketcher.Constraint('Tangent',       lastID + 2,2,  lastID + 3,1))						#Constraints[4]
	constraintList.append(Sketcher.Constraint('Tangent',       lastID + 3,2,  lastID + 4,2))						#Constraints[5]
	constraintList.append(Sketcher.Constraint('Equal',         lastID + 0,    lastID + 1))						#Constraints[6]
	constraintList.append(Sketcher.Constraint('Equal',         lastID + 1,    lastID + 2))						#Constraints[7]
	constraintList.append(Sketcher.Constraint('Equal',         lastID + 2,    lastID + 3))						#Constraints[8]
	constraintList.append(Sketcher.Constraint('Equal',         lastID + 6,    lastID + 10))						#Constraints[9]
	constraintList.append(Sketcher.Constraint('Equal',         lastID + 8,    lastID + 11))						#Constraints[10]
	constraintList.append(Sketcher.Constraint('Equal',         lastID + 6,    lastID + 12))						#Constraints[11]
	constraintList.append(Sketcher.Constraint('Equal',         lastID + 8,    lastID + 13))						#Constraints[12]
	constraintList.append(Sketcher.Constraint('Coincident',    lastID + 0,2,  lastID + 6,1))						#Constraints[13]
	constraintList.append(Sketcher.Constraint('Coincident',    lastID + 6,2,  lastID + 0,3))						#Constraints[14]
	constraintList.append(Sketcher.Constraint('Coincident',    lastID + 0,1,  lastID + 7,2))						#Constraints[15]
	constraintList.append(Sketcher.Constraint('Coincident',    lastID + 7,1,  lastID + 0,3))						#Constraints[16]
	constraintList.append(Sketcher.Constraint('Coincident',    lastID + 2,2,  lastID + 8,1))						#Constraints[17]
	constraintList.append(Sketcher.Constraint('Coincident',    lastID + 8,2,  lastID + 2,3))						#Constraints[18]
	constraintList.append(Sketcher.Constraint('Coincident',    lastID + 2,1,  lastID + 9,2))						#Constraints[19]
	constraintList.append(Sketcher.Constraint('Coincident',    lastID + 9,1,  lastID + 2,3))						#Constraints[20]
	constraintList.append(Sketcher.Constraint('Coincident',    lastID + 10,2, lastID + 4,1))						#Constraints[21]
	constraintList.append(Sketcher.Constraint('Coincident',    lastID + 11,2, lastID + 4,2))						#Constraints[22]
	constraintList.append(Sketcher.Constraint('Coincident',    lastID + 12,2, lastID + 5,1))						#Constraints[23]
	constraintList.append(Sketcher.Constraint('Coincident',    lastID + 13,2, lastID + 5,2))						#Constraints[24]
	constraintList.append(Sketcher.Constraint('Perpendicular', lastID + 7,    lastID + 6))						#Constraints[25]
	constraintList.append(Sketcher.Constraint('Perpendicular', lastID + 9,    lastID + 8))						#Constraints[26]
	constraintList.append(Sketcher.Constraint('Perpendicular', lastID + 10,   lastID + 7))						#Constraints[27]
	constraintList.append(Sketcher.Constraint('Perpendicular', lastID + 11,   lastID + 9))						#Constraints[28]
	constraintList.append(Sketcher.Constraint('Perpendicular', lastID + 12,   lastID + 7))						#Constraints[29]
	constraintList.append(Sketcher.Constraint('Perpendicular', lastID + 13,   lastID + 9))						#Constraints[30]
	constraintList.append(Sketcher.Constraint('Symmetric',     lastID + 1,3,  lastID + 3,3,  lastID + 16,1))		#Constraints[31]
	constraintList.append(Sketcher.Constraint('Distance',      lastID + 10,1, lastID + 11,1, 2*Dist_X))			#Constraints[32]
	constraintList.append(Sketcher.Constraint('Distance',      lastID + 10,1, lastID + 12,1, 2*Dist_Y))			#Constraints[33]
	constraintList.append(Sketcher.Constraint('Coincident',    lastID + 16,1, lastID + 14,1))						#Constraints[34]
	constraintList.append(Sketcher.Constraint('Horizontal',    lastID + 14))										#Constraints[35]
	constraintList.append(Sketcher.Constraint('DistanceX',     lastID + 14,1, lastID + 14,2, Radio))				#Constraints[36]
	constraintList.append(Sketcher.Constraint('Coincident',    lastID + 16,1, lastID + 15,1))						#Constraints[37]
	constraintList.append(Sketcher.Constraint('Parallel',      lastID + 15,   lastID + 4))						#Constraints[38]
	constraintList.append(Sketcher.Constraint('Distance',      lastID + 15,1, lastID + 15,2, Radio))				#Constraints[39]
	constraintList.append(Sketcher.Constraint('Angle',         lastID + 14,1, lastID + 15,1, Angulo))				#Constraints[40]
	constraintList.append(Sketcher.Constraint('DistanceX',     lastID + 16,1, Pt1.x))								#Constraints[41]
	constraintList.append(Sketcher.Constraint('DistanceY',     lastID + 16,1, Pt1.y))								#Constraints[42]
	
	Boceto_X.addConstraint(constraintList)
	
	del constraintList
	
	Doc.recompute
	
	
	
def Crear_Semicirculo(Pt1, Boceto_X, Dist_X = False, Dist_Y = False, Tipo = 'B', Angulo = 0, Radio_Centro = False, Guia = False, Grupo = '-'):
	
	# Tipos:
	#	A => Semicirculo
	#	B => Semicirculo + Cuadrado
	
	# validar entrada
	if Dist_X == False:
		Dist_X = 100
	else:
		Dist_X = Dist_X / 2
	if Dist_Y == False:
		Dist_Y = 200
	if Dist_Y - Dist_X > 0:
		Largo = Dist_Y - Dist_X
	else:
		Tipo = 'A'
	Radio = Dist_X
	
	lastID = len(Boceto_X.Geometry)
	
	# creamos la lista de puntos por cada arco
	geoList = []
	# [centro curva, Eje, Radio, Angulo inicial, Angulo final]
	geoList.append([App.Vector(Pt1.x, Pt1.y, Pt1.z), App.Vector(0, 0, 1), Radio, math.radians( 0), math.radians( 90)])			#Object[A0,B0]
	geoList.append([App.Vector(Pt1.x, Pt1.y, Pt1.z), App.Vector(0, 0, 1), Radio, math.radians(90), math.radians(180)])			#Object[A1,B0]
	
	for NewArco in geoList:
		if Guia == False:
			# Crear_Arco(Pt1, Eje, Radio, Boceto_X, Ang_Ini, Ang_Fin, Guia = False, Grupo_X = '-'):
			Crear_Arco(NewArco[0], NewArco[1], NewArco[2], Boceto_X, NewArco[3], NewArco[4], Guia, Grupo)
		else:
			# Crear_Arco(Pt1, Eje, Radio, Boceto_X, Ang_Ini, Ang_Fin, Guia = False, Grupo_X = '-'):
			Crear_Arco(NewArco[0], NewArco[1], NewArco[2], Boceto_X, NewArco[3], NewArco[4], Guia, Grupo + '_G')
	
	del geoList
	
	# creamos la lista de puntos por cada linea
	geoList = []
	if Tipo == 'A':
		# [Punto inicial, Punto final]
		geoList.append([App.Vector(-Dist_X + Pt1.x, Pt1.y, Pt1.z), App.Vector(Dist_X + Pt1.x, Pt1.y, Pt1.z)])						#Object[A2]
	if Tipo == 'B':
		# [Punto inicial, Punto final]
		geoList.append([App.Vector(-Dist_X + Pt1.x, -Largo + Pt1.y, Pt1.z), App.Vector( Dist_X + Pt1.x, -Largo + Pt1.y, Pt1.z)])	#Object[B2]
		geoList.append([App.Vector(-Dist_X + Pt1.x,          Pt1.y, Pt1.z), App.Vector(-Dist_X + Pt1.x, -Largo + Pt1.y, Pt1.z)])	#Object[B3]
		geoList.append([App.Vector( Dist_X + Pt1.x,          Pt1.y, Pt1.z), App.Vector( Dist_X + Pt1.x, -Largo + Pt1.y, Pt1.z)])	#Object[B4]
		
	for NewLinea in geoList:
		if Guia == False:
			# Crear_Linea(Pt1, Pt2, Boceto_X, Guia = False, Grupo_X = '-'):
			Crear_Linea(NewLinea[0], NewLinea[1], Boceto_X, Guia, Grupo)
		else:
			# Crear_Linea(Pt1, Pt2, Boceto_X, Guia = False, Grupo_X = '-'):
			Crear_Linea(NewLinea[0], NewLinea[1], Boceto_X, Guia, Grupo + '_G')
	
	del geoList
	
	# creamos la lista de puntos por cada linea auxiliar
	geoList = []
	# [Punto inicial, Punto final]
	geoList.append([App.Vector(-Dist_X + Pt1.x, Pt1.y, Pt1.z), App.Vector(-Dist_X + Pt1.x, Radio + Pt1.y, Pt1.z)])		#Object[A3,B5]
	geoList.append([App.Vector(          Pt1.x, Pt1.y, Pt1.z), App.Vector(          Pt1.x, Radio + Pt1.y, Pt1.z)])		#Object[A4,B6]
	geoList.append([App.Vector( Dist_X + Pt1.x, Pt1.y, Pt1.z), App.Vector( Dist_X + Pt1.x, Radio + Pt1.y, Pt1.z)])		#Object[A5,B7]
	
	geoList.append([App.Vector( Pt1.x, Pt1.y, Pt1.z),          App.Vector(Radio + Pt1.x, Pt1.y, Pt1.z)])					#Object[A6,B8]
	geoList.append([App.Vector( Pt1.x, Pt1.y, Pt1.z),          App.Vector(Radio + Pt1.x, Pt1.y, Pt1.z)])					#Object[A7,B9]
	if Tipo == 'B':
		# [Punto inicial, Punto final]
		geoList.append([App.Vector(-Dist_X + Pt1.x, Pt1.y, Pt1.z), App.Vector(Dist_X + Pt1.x, Pt1.y, Pt1.z)])				#Object[B10]
		
	for NewLinea in geoList:
		# Crear_Linea(Pt1, Pt2, Boceto_X, Guia = False, Grupo_X = '-'):
		Crear_Linea(NewLinea[0], NewLinea[1], Boceto_X, True, Grupo + '_G')
	
	del geoList
	
	# creamos la lista de puntos auxiliares
	geoList = []
	# [Punto inicial]
	geoList.append([App.Vector(Pt1.x, Radio / 2 + Pt1.y, Pt1.z)])														#Object[A8,B11]
	
	for NewPunto in geoList:
		# Crear_Punto(Pt1, Boceto_X, Guia = False, Grupo_X = '-'):
		Crear_Punto(NewPunto[0], Boceto_X, True, Grupo + '_G')
		
	del geoList
	
	if Radio_Centro != False:
		# Crear_Circulo(Pt1, Eje, Radio, Boceto_X, Guia = False, Grupo_X = '-'):
		Crear_Circulo(App.Vector(Pt1.x, Pt1.y, Pt1.z), App.Vector(0, 0, 1), Radio_Centro, Boceto_X, Grupo_X = Grupo)		#Object[B12]
	
	# creamos la lista de restricciones
	constraintList = []
	constraintList.append(Sketcher.Constraint('Coincident',         lastID + 1,3, lastID + 0,3))					#Constraints[A0,B0]
	constraintList.append(Sketcher.Constraint('Coincident',         lastID + 1,1, lastID + 0,2))					#Constraints[A1,B1]
	if Tipo == 'A':
		constraintList.append(Sketcher.Constraint('Coincident',     lastID + 2,1, lastID + 1,2))					#Constraints[A2]
		constraintList.append(Sketcher.Constraint('Coincident',     lastID + 2,2, lastID + 0,1))					#Constraints[A3]
		constraintList.append(Sketcher.Constraint('PointOnObject',  lastID + 0,3, lastID + 2))					#Constraints[A4]
		constraintList.append(Sketcher.Constraint('Coincident',     lastID + 4,1, lastID + 0,3))					#Constraints[A5]
		constraintList.append(Sketcher.Constraint('Coincident',     lastID + 4,2, lastID + 0,2))					#Constraints[A6]
		constraintList.append(Sketcher.Constraint('Coincident',     lastID + 3,1, lastID + 1,2))					#Constraints[A7]
		constraintList.append(Sketcher.Constraint('Coincident',     lastID + 5,1, lastID + 0,1))					#Constraints[A8]
		constraintList.append(Sketcher.Constraint('Perpendicular',  lastID + 4,   lastID + 2))					#Constraints[A9]
		constraintList.append(Sketcher.Constraint('Perpendicular',  lastID + 3,   lastID + 2))					#Constraints[A10]
		constraintList.append(Sketcher.Constraint('Perpendicular',  lastID + 5,   lastID + 2))					#Constraints[A11]
		constraintList.append(Sketcher.Constraint('Equal',          lastID + 4,   lastID + 5))					#Constraints[A12]
		constraintList.append(Sketcher.Constraint('Equal',          lastID + 4,   lastID + 3))					#Constraints[A13]
		constraintList.append(Sketcher.Constraint('Symmetric',      lastID + 1,2, lastID + 5,2, lastID + 8,1))	#Constraints[A14]
		constraintList.append(Sketcher.Constraint('Distance',       lastID + 3,2, lastID + 5,2, 2*Dist_X))		#Constraints[A15]
		constraintList.append(Sketcher.Constraint('Coincident',     lastID + 8,1, lastID + 6,1))					#Constraints[A16]
		constraintList.append(Sketcher.Constraint('Horizontal',     lastID + 6))									#Constraints[A17]
		constraintList.append(Sketcher.Constraint('DistanceX',      lastID + 6,1, lastID + 6,2, Radio))			#Constraints[A18]
		constraintList.append(Sketcher.Constraint('Coincident',     lastID + 8,1, lastID + 7,1))					#Constraints[A19]
		constraintList.append(Sketcher.Constraint('Parallel',       lastID + 7,   lastID + 2))					#Constraints[A20]
		constraintList.append(Sketcher.Constraint('Distance',       lastID + 7,1, lastID + 7,2, Radio))			#Constraints[A21]
		constraintList.append(Sketcher.Constraint('Angle',          lastID + 6,1, lastID + 7,1, Angulo))			#Constraints[A22]
		constraintList.append(Sketcher.Constraint('DistanceX',      lastID + 8,1, Pt1.x))							#Constraints[A23]
		constraintList.append(Sketcher.Constraint('DistanceY',      lastID + 8,1, Pt1.y))							#Constraints[A24]
	
	if Tipo == 'B':
		constraintList.append(Sketcher.Constraint('Coincident',     lastID + 10,1, lastID + 1,2))					#Constraints[B2]
		constraintList.append(Sketcher.Constraint('Coincident',     lastID + 10,2, lastID + 0,1))					#Constraints[B3]
		constraintList.append(Sketcher.Constraint('PointOnObject',  lastID + 0,3,  lastID + 10))					#Constraints[B4]
		if Radio_Centro != False:
			constraintList.append(Sketcher.Constraint('Coincident', lastID + 0,3,  lastID + 12,3))				#Constraints[B4.1]
			constraintList.append(Sketcher.Constraint('Radius',     lastID + 12,   Radio_Centro))					#Constraints[B4.2]
		constraintList.append(Sketcher.Constraint('Coincident',     lastID + 6,1,  lastID + 0,3))					#Constraints[B5]
		constraintList.append(Sketcher.Constraint('Coincident',     lastID + 6,2,  lastID + 0,2))					#Constraints[B6]
		constraintList.append(Sketcher.Constraint('Coincident',     lastID + 5,1,  lastID + 1,2))					#Constraints[B7]
		constraintList.append(Sketcher.Constraint('Coincident',     lastID + 7,1,  lastID + 0,1))					#Constraints[B8]
		constraintList.append(Sketcher.Constraint('Coincident',     lastID + 3,1,  lastID + 1,2))					#Constraints[B9]
		constraintList.append(Sketcher.Constraint('Coincident',     lastID + 3,2,  lastID + 2,1))					#Constraints[B10]
		constraintList.append(Sketcher.Constraint('Coincident',     lastID + 2,2,  lastID + 4,2))					#Constraints[B11]
		constraintList.append(Sketcher.Constraint('Coincident',     lastID + 4,1,  lastID + 0,1))					#Constraints[B12]
		constraintList.append(Sketcher.Constraint('Perpendicular',  lastID + 6,    lastID + 10))					#Constraints[B13]
		constraintList.append(Sketcher.Constraint('Perpendicular',  lastID + 5,    lastID + 10))					#Constraints[B14]
		constraintList.append(Sketcher.Constraint('Perpendicular',  lastID + 7,    lastID + 10))					#Constraints[B15]
		constraintList.append(Sketcher.Constraint('Perpendicular',  lastID + 3,    lastID + 10))					#Constraints[B16]
		constraintList.append(Sketcher.Constraint('Perpendicular',  lastID + 4,    lastID + 10))					#Constraints[B17]
		constraintList.append(Sketcher.Constraint('Parallel',       lastID + 10,   lastID + 2))					#Constraints[B18]
		constraintList.append(Sketcher.Constraint('Equal',          lastID + 6,    lastID + 7))					#Constraints[B19]
		constraintList.append(Sketcher.Constraint('Equal',          lastID + 6,    lastID + 5))					#Constraints[B20]
		constraintList.append(Sketcher.Constraint('Symmetric',      lastID + 5,2,  lastID + 2,2, lastID + 11,1))	#Constraints[B21]
		constraintList.append(Sketcher.Constraint('Distance',       lastID + 5,2,  lastID + 7,2, 2*Dist_X))		#Constraints[B22]
		constraintList.append(Sketcher.Constraint('Distance',       lastID + 7,2,  lastID + 2,2, Dist_Y))			#Constraints[B23]
		constraintList.append(Sketcher.Constraint('Coincident',     lastID + 11,1, lastID + 8,1))					#Constraints[B24]
		constraintList.append(Sketcher.Constraint('Horizontal',     lastID + 8))									#Constraints[B25]
		constraintList.append(Sketcher.Constraint('DistanceX',      lastID + 8,1,  lastID + 8,2, Radio))			#Constraints[B26]
		constraintList.append(Sketcher.Constraint('Coincident',     lastID + 11,1, lastID + 9,1))					#Constraints[B27]
		constraintList.append(Sketcher.Constraint('Parallel',       lastID + 9,    lastID + 10))					#Constraints[B28]
		constraintList.append(Sketcher.Constraint('Distance',       lastID + 9,1,  lastID + 9,2, Radio))			#Constraints[B29]
		constraintList.append(Sketcher.Constraint('Angle',          lastID + 8,1,  lastID + 9,1, Angulo))			#Constraints[B30]
		constraintList.append(Sketcher.Constraint('DistanceX',      lastID + 11,1, Pt1.x))						#Constraints[B31]
		constraintList.append(Sketcher.Constraint('DistanceY',      lastID + 11,1, Pt1.y))						#Constraints[B32]
	
	Boceto_X.addConstraint(constraintList)
	
	del constraintList
	
	Doc.recompute
	
	
	
def Crear_Estrella(Pt1, Boceto_X, Radio1, Radio2, Puntas = 5, Angulo = 0, Tipo = 'TA', Radio3 = 5, Angulo2 = 0, Grupo = '-'):
	
	# Tipos de estrellas
	# TA = Normal
	# TB = dos puntas diferentes
	
	lastID = len(Boceto_X.Geometry)
	
	# creamos la lista de puntos por cada circulo
	geoList = []
	# [centro curva, Eje, Radio, Angulo inicial, Angulo final]
	geoList.append([App.Vector(Pt1.x, Pt1.y, Pt1.z), App.Vector(0, 0, 1), Radio1])		#Object[A0,B0]
	geoList.append([App.Vector(Pt1.x, Pt1.y, Pt1.z), App.Vector(0, 0, 1), Radio2])		#Object[A1,B1]
	if Tipo == 'TB':
		geoList.append([App.Vector(Pt1.x, Pt1.y, Pt1.z), App.Vector(0, 0, 1), Radio3])	#Object[B2]
	
	for NewCirculo in geoList:
		# Crear_Circulo(Pt1, Eje, Radio, Boceto_X, Guia = False, Grupo_X = '-'):
		Crear_Circulo(NewCirculo[0], NewCirculo[1], NewCirculo[2], Boceto_X, True, Grupo + '_G')
	
	del geoList
	
	# creamos la lista de puntos por cada linea auxiliar
	geoList = []
	# [Punto inicial, Punto final]
	geoList.append([App.Vector(Pt1.x, Pt1.y, Pt1.z), App.Vector(Pt1.x + Radio1, Pt1.y, Pt1.z)])	#Object[A2,B3]
	geoList.append([App.Vector(Pt1.x, Pt1.y, Pt1.z), App.Vector(Pt1.x + Radio2, Pt1.y, Pt1.z)])	#Object[A3,B4]
	
	for NewLinea in geoList:
		# Crear_Linea(Pt1, Pt2, Boceto_X, Guia = False, Grupo_X = '-'):
		Crear_Linea(NewLinea[0], NewLinea[1], Boceto_X, True, Grupo + '_G')
	
	del geoList
	
	Ang = 360 / Puntas
	Ang2 = Ang / 2
	
	if Tipo == 'TB':
		Ang3 = Ang2
		Ang2 = Ang2 / 2
		Dx = Radio1 - Radio2 * math.cos(math.radians(Ang3))
		Dy = Radio2 * math.sin(math.radians(Ang3))
		AngMax = 2 * math.atan2(Dy, Dx)
		Angulo2 = abs(Angulo2)
		if Angulo2 >= AngMax:
			Angulo2 = AngMax - 1
	
	if Angulo2 == 0:
		Dx = Radio1 - Radio2 * math.cos(math.radians(Ang2))
		Dy = Radio2 * math.sin(math.radians(Ang2))
		Angulo2 = 2 * math.atan2(Dy, Dx)
	
	# creamos la lista de puntos por cada linea
	geoList = []
	for k in range(0, Puntas):
		Rx = Radio1 * math.cos(math.radians(k * Ang))
		Ry = Radio1 * math.sin(math.radians(k * Ang))
		R1x = Radio2 * math.cos(math.radians(k * Ang - Ang2))
		R1y = Radio2 * math.sin(math.radians(k * Ang - Ang2))
		R2x = Radio2 * math.cos(math.radians(k * Ang + Ang2))
		R2y = Radio2 * math.sin(math.radians(k * Ang + Ang2))
		if Tipo == 'TB':
			R3x = Radio3 * math.cos(math.radians(k * Ang + Ang3))
			R3y = Radio3 * math.sin(math.radians(k * Ang + Ang3))
			R4x = Radio2 * math.cos(math.radians(k * Ang - Ang2 + Ang3))
			R4y = Radio2 * math.sin(math.radians(k * Ang - Ang2 + Ang3))
			R5x = Radio2 * math.cos(math.radians(k * Ang + Ang2 + Ang3))
			R5y = Radio2 * math.sin(math.radians(k * Ang + Ang2 + Ang3))
		
		# [Punto inicial, Punto final]
		geoList.append([App.Vector(Pt1.x + Rx, Pt1.y + Ry, Pt1.z), App.Vector(Pt1.x + R1x, Pt1.y + R1y, Pt1.z)])			#Object[A4,B5]
		geoList.append([App.Vector(Pt1.x + Rx, Pt1.y + Ry, Pt1.z), App.Vector(Pt1.x + R2x, Pt1.y + R2y, Pt1.z)])			#Object[An,Bn]
		if Tipo == 'TB':
			geoList.append([App.Vector(Pt1.x + R3x, Pt1.y + R3y, Pt1.z), App.Vector(Pt1.x + R4x, Pt1.y + R4y, Pt1.z)])	#Object[Bn+1]
			geoList.append([App.Vector(Pt1.x + R3x, Pt1.y + R3y, Pt1.z), App.Vector(Pt1.x + R5x, Pt1.y + R5y, Pt1.z)])	#Object[Bm]
		
	for NewLinea in geoList:
		# Crear_Linea(Pt1, Pt2, Boceto_X, Guia = False, Grupo_X = '-'):
		Crear_Linea(NewLinea[0], NewLinea[1], Boceto_X, Grupo_X = Grupo)
	
	del geoList
	
	Doc.recompute
	
	# creamos la lista de restricciones
	constraintList = []
	# hacemos los circulos concentricos
	constraintList.append(Sketcher.Constraint('Coincident',        lastID + 0,3, lastID + 1,3))	#Constraints[A0,B0]
	if Tipo == 'TB':
		constraintList.append(Sketcher.Constraint('Coincident',    lastID + 0,3, lastID + 2,3))	#Constraints[B1]
	# fijamos las lineas guias a los circulos guia
	if Tipo == 'TA':
		constraintList.append(Sketcher.Constraint('Coincident',    lastID + 0,3, lastID + 2,1))	#Constraints[A1]
		constraintList.append(Sketcher.Constraint('Coincident',    lastID + 0,3, lastID + 3,1))	#Constraints[A2]
		constraintList.append(Sketcher.Constraint('PointOnObject', lastID + 2,2, lastID + 0))		#Constraints[A2]
		constraintList.append(Sketcher.Constraint('PointOnObject', lastID + 3,2, lastID + 1))		#Constraints[A3]
		constraintList.append(Sketcher.Constraint('Horizontal',    lastID + 3))					#Constraints[A4]
	if Tipo == 'TB':
		constraintList.append(Sketcher.Constraint('Coincident',    lastID + 0,3, lastID + 3,1))	#Constraints[B2]
		constraintList.append(Sketcher.Constraint('Coincident',    lastID + 0,3, lastID + 4,1))	#Constraints[B3]
		constraintList.append(Sketcher.Constraint('PointOnObject', lastID + 3,2, lastID + 0))		#Constraints[B4]
		constraintList.append(Sketcher.Constraint('PointOnObject', lastID + 4,2, lastID + 1))		#Constraints[B5]
		constraintList.append(Sketcher.Constraint('Horizontal',    lastID + 4))					#Constraints[B6]
	# fijamos el radio de cada circulo guia
	constraintList.append(Sketcher.Constraint('Radius',            lastID + 0, Radio1))			#Constraints[A5,B7]
	constraintList.append(Sketcher.Constraint('Radius',            lastID + 1, Radio2))			#Constraints[A6,B8]
	if Tipo == 'TB':
		constraintList.append(Sketcher.Constraint('Radius',        lastID + 2, Radio3))			#Constraints[B9]
	# unimos los extremos de dos lineas creando las puntas de la estrella
	for NewConstr in range(0, Puntas):
		if NewConstr == Puntas - 1:
			if Tipo == 'TA':
				constraintList.append(Sketcher.Constraint('Coincident', lastID + 2 * NewConstr + 4,1, lastID + 2 * NewConstr + 5,1))	#Constraints[A7]
				constraintList.append(Sketcher.Constraint('Coincident', lastID + 2 * NewConstr + 5,2, lastID + 4,2))					#Constraints[A8]
			if Tipo == 'TB':
				constraintList.append(Sketcher.Constraint('Coincident', lastID + 4 * NewConstr + 5,1, lastID + 4 * NewConstr + 6,1))	#Constraints[B10]
				constraintList.append(Sketcher.Constraint('Coincident', lastID + 4 * NewConstr + 6,2, lastID + 4 * NewConstr + 7,2))	#Constraints[B11]
				constraintList.append(Sketcher.Constraint('Coincident', lastID + 4 * NewConstr + 7,1, lastID + 4 * NewConstr + 8,1))	#Constraints[B12]
				constraintList.append(Sketcher.Constraint('Coincident', lastID + 4 * NewConstr + 8,2, lastID + 5,2))					#Constraints[B13]
		else:
			if Tipo == 'TA':
				constraintList.append(Sketcher.Constraint('Coincident', lastID + 2 * NewConstr + 4,1, lastID + 2 * NewConstr + 5,1))	#Constraints[A7]
				constraintList.append(Sketcher.Constraint('Coincident', lastID + 2 * NewConstr + 5,2, lastID + 2 * NewConstr + 6,2))	#Constraints[A8]
			if Tipo == 'TB':
				constraintList.append(Sketcher.Constraint('Coincident', lastID + 4 * NewConstr + 5,1, lastID + 4 * NewConstr + 6,1))	#Constraints[B10]
				constraintList.append(Sketcher.Constraint('Coincident', lastID + 4 * NewConstr + 6,2, lastID + 4 * NewConstr + 7,2))	#Constraints[B11]
				constraintList.append(Sketcher.Constraint('Coincident', lastID + 4 * NewConstr + 7,1, lastID + 4 * NewConstr + 8,1))	#Constraints[B12]
				constraintList.append(Sketcher.Constraint('Coincident', lastID + 4 * NewConstr + 8,2, lastID + 4 * NewConstr + 9,2))	#Constraints[B13]
	# unimos la linea guia a la primer punta de la estrella
	if Tipo == 'TA':
		constraintList.append(Sketcher.Constraint('Coincident', lastID + 2,2, lastID + 4,1))									#Constraints[A9]
	if Tipo == 'TB':
		constraintList.append(Sketcher.Constraint('Coincident', lastID + 3,2, lastID + 5,1))									#Constraints[B14]
	# igulamos las lineas de cada punta de la estrella
	if Tipo == 'TA':
		for NewConstr in range(0, 2 * Puntas - 1):
			constraintList.append(Sketcher.Constraint('Equal', lastID + NewConstr + 4, lastID + NewConstr + 5))				#Constraints[A10]
	if Tipo == 'TB':
		for NewConstr in range(0, 4 * Puntas - 2, 4):
			constraintList.append(Sketcher.Constraint('Equal', lastID + NewConstr + 5, lastID + NewConstr + 6))				#Constraints[B15]
			constraintList.append(Sketcher.Constraint('Equal', lastID + NewConstr + 7, lastID + NewConstr + 8))				#Constraints[B16]
		for NewConstr in range(0, 4 * Puntas - 4, 4):
			constraintList.append(Sketcher.Constraint('Equal', lastID + NewConstr + 6, lastID + NewConstr + 9))				#Constraints[B17]
			constraintList.append(Sketcher.Constraint('Equal', lastID + NewConstr + 8, lastID + NewConstr + 11))				#Constraints[B18]
	# unimos las puntas de la estrella a los circulos guia
	for NewConstr in range(0, Puntas):
		if Tipo == 'TA':
			if NewConstr != 0:
				constraintList.append(Sketcher.Constraint('PointOnObject', lastID + 2 * NewConstr + 4,1,  lastID + 0))		#Constraints[A11]
			constraintList.append(Sketcher.Constraint('PointOnObject',     lastID + 2 * NewConstr + 5,2,  lastID + 1))		#Constraints[A12]
		if Tipo == 'TB':
			if NewConstr != 0:
				constraintList.append(Sketcher.Constraint('PointOnObject', lastID + 4 * NewConstr + 5,1,  lastID + 0))		#Constraints[B19]
			constraintList.append(Sketcher.Constraint('PointOnObject',     lastID + 4 * NewConstr + 6,2,  lastID + 1))		#Constraints[B20]
			constraintList.append(Sketcher.Constraint('PointOnObject',     lastID + 4 * NewConstr + 7,1,  lastID + 2))		#Constraints[B21]
			constraintList.append(Sketcher.Constraint('PointOnObject',     lastID + 4 * NewConstr + 8,2,  lastID + 1))		#Constraints[B22]
	# ubicamos la posicion y el angulo de la estrella
	if Tipo == 'TA':
		constraintList.append(Sketcher.Constraint('Angle', lastID + 3,1, lastID + 2,1, Angulo))								#Constraints[A13]
	if Tipo == 'TB':
		constraintList.append(Sketcher.Constraint('Angle', lastID + 6,1, lastID + 5,1, Angulo2))
		constraintList.append(Sketcher.Constraint('Angle', lastID + 4,1, lastID + 3,1, Angulo))								#Constraints[B23]
	constraintList.append(Sketcher.Constraint('DistanceX', lastID + 0,3, Pt1.x))												#Constraints[A14,B24]
	constraintList.append(Sketcher.Constraint('DistanceY', lastID + 0,3, Pt1.y))												#Constraints[A15,B25]
	
	Boceto_X.addConstraint(constraintList)
	
	del constraintList
	
	Doc.recompute
	
	
	
def Crear_Keyhole(Pt1, Boceto_X, Radio1, Radio2, Largo, Angulo = 0, Tipo = 'TA', Grupo = '-'):
	
	lastID = len(Boceto_X.Geometry)
	
	if Tipo == 'TA':
		h = Largo - Radio1 - Radio2
		j = Largo / 2 - Radio1
	if Tipo == 'TB':
		h = Largo - Radio2
		j = Largo / 2
	k = Largo / 2 - Radio2
	Ang1 = math.pi - math.acos(Radio1 / Radio2)
	Ang2 = 2 * math.pi + math.acos(Radio1 / Radio2)
	d = math.sqrt(math.pow(Radio2, 2) - math.pow(Radio1, 2))
	
	# creamos la lista de puntos por cada linea auxiliar
	geoList = []
	# [Punto inicial, Punto final]
	geoList.append([App.Vector(Pt1.x, Pt1.y + h, Pt1.z), App.Vector(Pt1.x, Pt1.y, Pt1.z)])								#Object[A0,B0]
	geoList.append([App.Vector(Pt1.x, Pt1.y + k, Pt1.z), App.Vector(Pt1.x + Radio1, Pt1.y + k, Pt1.z)])					#Object[A1,B1]
	geoList.append([App.Vector(Pt1.x, Pt1.y + k, Pt1.z), App.Vector(Pt1.x + Radio2, Pt1.y + k, Pt1.z)])					#Object[A2,B2]
	
	for NewLinea in geoList:
		# Crear_Linea(Pt1, Pt2, Boceto_X, Guia = False, Grupo_X = '-'):
		Crear_Linea(NewLinea[0], NewLinea[1], Boceto_X, True, Grupo + '_G')
	
	del geoList
	
	# creamos la lista de puntos por cada arco
	geoList = []
	# [centro curva, Eje, Radio, Angulo inicial, Angulo final]
	if Tipo == 'TA':
		geoList.append([App.Vector(Pt1.x, Pt1.y + h, Pt1.z), App.Vector(0, 0, 1), Radio1, math.radians(0), math.radians(180)])	#Object[A3]
	geoList.append([App.Vector(Pt1.x, Pt1.y, Pt1.z), App.Vector(0, 0, 1), Radio2, Ang1, Ang2])									#Object[A4,B3]
	
	for NewArco in geoList:
		# Crear_Arco(Pt1, Eje, Radio, Boceto_X, Ang_Ini, Ang_Fin, Guia = False, Grupo_X = '-'):
		Crear_Arco(NewArco[0], NewArco[1], NewArco[2], Boceto_X, NewArco[3], NewArco[4], Grupo_X = Grupo)
	
	del geoList
	
	# creamos la lista de puntos por cada linea
	geoList = []
	# [Punto inicial, Punto final]
	if Tipo == 'TB':
		geoList.append([App.Vector(Pt1.x - Radio1, Pt1.y + h, Pt1.z), App.Vector(Pt1.x + Radio1, Pt1.y + h, Pt1.z)])	#Object[B4]
	geoList.append([App.Vector(Pt1.x - Radio1, Pt1.y + h, Pt1.z), App.Vector(Pt1.x - Radio1, Pt1.y + d, Pt1.z)])		#Object[A5,B5]
	geoList.append([App.Vector(Pt1.x + Radio1, Pt1.y + h, Pt1.z), App.Vector(Pt1.x + Radio1, Pt1.y + d, Pt1.z)])		#Object[A6,B6]
	
	for NewLinea in geoList:
		# Crear_Linea(Pt1, Pt2, Boceto_X, Guia = False, Grupo_X = '-'):
		Crear_Linea(NewLinea[0], NewLinea[1], Boceto_X, Grupo_X = Grupo)
	
	del geoList
	
	# creamos la lista de restricciones
	constraintList = []
	# fijamos las lineas guias		
	constraintList.append(Sketcher.Constraint('Distance',          lastID + 0,2, lastID + 1,1, k))				#Constraints[A0,B0]
	constraintList.append(Sketcher.Constraint('Distance',          lastID + 0,1, lastID + 1,1, j))				#Constraints[A1,B1]
	constraintList.append(Sketcher.Constraint('PointOnObject',     lastID + 1,1, lastID + 0))						#Constraints[A2,B2]
	constraintList.append(Sketcher.Constraint('Coincident',        lastID + 1,1, lastID + 2,1))					#Constraints[A3,B3]
	constraintList.append(Sketcher.Constraint('Horizontal',        lastID + 1))									#Constraints[A4,B4]
	constraintList.append(Sketcher.Constraint('Perpendicular',     lastID + 0,   lastID + 2))						#Constraints[A5,B4]
	constraintList.append(Sketcher.Constraint('Distance',          lastID + 1,   Radio1))							#Constraints[A6,B6]
	constraintList.append(Sketcher.Constraint('Distance',          lastID + 2,   Radio2))							#Constraints[A7,B7]
	# fijamos los arcos a la linea guia
	if Tipo == 'TA':
		constraintList.append(Sketcher.Constraint('Coincident',    lastID + 3,3, lastID + 0,1))					#Constraints[A8]
		constraintList.append(Sketcher.Constraint('Coincident',    lastID + 0,2, lastID + 4,3))					#Constraints[A9]
		constraintList.append(Sketcher.Constraint('Radius',        lastID + 3,   Radio1))							#Constraints[A10]
		constraintList.append(Sketcher.Constraint('Radius',        lastID + 4,   Radio2))							#Constraints[A11]
	if Tipo == 'TB':
		constraintList.append(Sketcher.Constraint('Symmetric',     lastID + 4,1, lastID + 4,2, lastID + 0,1))		#Constraints[B8]
		constraintList.append(Sketcher.Constraint('Coincident',    lastID + 0,2, lastID + 3,3))					#Constraints[B9]
		constraintList.append(Sketcher.Constraint('Distance',      lastID + 0,1, lastID + 4,2, Radio1))			#Constraints[B10]
		constraintList.append(Sketcher.Constraint('Radius',        lastID + 3,   Radio2))							#Constraints[B11]
	# ajustamos las lineas
	constraintList.append(Sketcher.Constraint('Parallel',          lastID + 0,   lastID + 5))						#Constraints[A12,B12]
	constraintList.append(Sketcher.Constraint('Parallel',          lastID + 0,   lastID + 6))						#Constraints[A13,B13]
	if Tipo == 'TB':
		constraintList.append(Sketcher.Constraint('Perpendicular', lastID + 0,   lastID + 4))						#Constraints[B14]
	# unimos los puntos de las lineas con los arcos
	if Tipo == 'TA':
		constraintList.append(Sketcher.Constraint('Coincident',    lastID + 4,1, lastID + 5,2))					#Constraints[A14]
		constraintList.append(Sketcher.Constraint('Coincident',    lastID + 4,2, lastID + 6,2))					#Constraints[A15]
		constraintList.append(Sketcher.Constraint('Tangent',       lastID + 5,1, lastID + 3,2))					#Constraints[A16]
		constraintList.append(Sketcher.Constraint('Tangent',       lastID + 6,1, lastID + 3,1))					#Constraints[A17]
	if Tipo == 'TB':
		constraintList.append(Sketcher.Constraint('Coincident',    lastID + 4,1, lastID + 5,1))					#Constraints[B15]
		constraintList.append(Sketcher.Constraint('Coincident',    lastID + 4,2, lastID + 6,1))					#Constraints[B16]
		constraintList.append(Sketcher.Constraint('Coincident',    lastID + 3,1, lastID + 5,2))					#Constraints[B17]
		constraintList.append(Sketcher.Constraint('Coincident',    lastID + 3,2, lastID + 6,2))					#Constraints[B18]
	# ubicamos la posicion y el angulo
	constraintList.append(Sketcher.Constraint('Angle',             lastID + 1,1, lastID + 2,1, Angulo))			#Constraints[A18,B19]
	constraintList.append(Sketcher.Constraint('DistanceX',         lastID + 1,1, Pt1.x))							#Constraints[A19,B20]
	constraintList.append(Sketcher.Constraint('DistanceY',         lastID + 1,1, Pt1.y))							#Constraints[A20,B21]
	
	Boceto_X.addConstraint(constraintList)
	
	del constraintList
	
	Doc.recompute
	
	
	
#! Estos son las funciones para crear Modelado 3D
def Crear_Relleno(Titulo, Etiqueta = '', Objeto_X = False, Boceto_X = False):
	
	Relleno_X = Doc.addObject('PartDesign::Pad', Titulo)
	if Objeto_X == False:
		Doc.Tip = Relleno_X
	else:
		Objeto_X.addObject(Relleno_X)
	if Etiqueta == '':
		Relleno_X.Label = Titulo
	else:
		Relleno_X.Label = Etiqueta
	
	Relleno_X.Profile = (Boceto_X, [''])
	Relleno_X.ReferenceAxis = (Boceto_X, ['N_Axis'])
	Boceto_X.Visibility = False
	
	Doc.recompute()
	return Relleno_X
	
	
	
def Crear_Hueco(Titulo, Etiqueta = '', Objeto_X = False, Boceto_X = False):
	
	Hueco_X = Doc.addObject('PartDesign::Pocket', Titulo)
	if Objeto_X == False:
		Doc.Tip = Hueco_X
	else:
		Objeto_X.addObject(Hueco_X)
	if Etiqueta == '':
		Hueco_X.Label = Titulo
	else:
		Hueco_X.Label = Etiqueta
	
	Hueco_X.Profile = (Boceto_X, [''])
	Hueco_X.ReferenceAxis = (Boceto_X, ['N_Axis'])
	Boceto_X.Visibility = False
	
	Doc.recompute()
	return Hueco_X
	
	
	
def Crear_Revolucion(Titulo, Etiqueta = '', Objeto_X = False, Boceto_X = False, Eje_X = False, Angulo = 360, Reverso = 0):
	
	Rev_X = Doc.addObject('PartDesign::Revolution', Titulo)
	if Objeto_X == False:
		Doc.Tip = Rev_X
	else:
		Objeto_X.addObject(Rev_X)
	if Etiqueta == '':
		Rev_X.Label = Titulo
	else:
		Rev_X.Label = Etiqueta
	
	Rev_X.Profile = (Boceto_X, [''])
	if Eje_X == False:
		Rev_X.ReferenceAxis = (Boceto_X, ['V_Axis'])
	else:
		Rev_X.ReferenceAxis = (Eje_X, [''])
		Eje_X.Visibility = False
	Rev_X.Angle = Angulo
	Rev_X.Reversed = Reverso
	Boceto_X.Visibility = False
	
	Doc.recompute()
	return Rev_X
	
	
	
def Crear_Agujero(Titulo, Etiqueta = '', Objeto_X = False, Boceto_X = False, Plano_X = '', Modelado_X = ''):
	
	Agujero_X = Doc.addObject('PartDesign::Hole', Titulo)
	if Objeto_X == False:
		Doc.Tip = Agujero_X
	else:
		Objeto_X.addObject(Agujero_X)
	if Etiqueta == '':
		Agujero_X.Label = Titulo
	else:
		Agujero_X.Label = Etiqueta
	
	if Boceto_X == False:
		Agujero_X.Profile = (Modelado_X, [Plano_X])
	else:
		Agujero_X.Profile = (Boceto_X, [''])
		Boceto_X.Visibility = False
	
	Doc.recompute()
	return Agujero_X
	
	
	
def Actualizar_Lista(Boceto_X):
	
	for k in range(0, len(Boceto_X.Geometry))[::-1]:
		t = len(Lista_Obj) - k - 1
		g = len(Boceto_X.Geometry) - k - 1
		if Lista_Obj[t][6] == Boceto_X.Label:
			if Lista_Obj[t][5] == 'linea':
				Pt1_temp = [round(Boceto_X.Geometry[g].StartPoint[0],8), round(Boceto_X.Geometry[g].StartPoint[1],8), round(Boceto_X.Geometry[g].StartPoint[2],8)]
				Pt2_temp = [round(Boceto_X.Geometry[g].EndPoint[0],8),   round(Boceto_X.Geometry[g].EndPoint[1],8),   round(Boceto_X.Geometry[g].EndPoint[2],8)]
				Vector3 = App.Vector(Pt2_temp) - App.Vector(Pt1_temp)
				Longitud = round(Vector3.Length, 8)
				# Longitud
				Lista_Obj[t][1] = Longitud
				# Punto inicio
				Lista_Obj[t][2] = Pt1_temp
				# Punto final
				Lista_Obj[t][3] = Pt2_temp
			if Lista_Obj[t][5] == 'arco':
				Pt1_temp = [round(Boceto_X.Geometry[g].StartPoint[0], 8), round(Boceto_X.Geometry[g].StartPoint[1], 8), round(Boceto_X.Geometry[g].StartPoint[2], 8)]
				Pt2_temp = [round(Boceto_X.Geometry[g].EndPoint[0], 8),   round(Boceto_X.Geometry[g].EndPoint[1], 8),   round(Boceto_X.Geometry[g].EndPoint[2], 8)]
				Eje_temp = [round(Boceto_X.Geometry[g].Center[0], 8),     round(Boceto_X.Geometry[g].Center[1], 8),     round(Boceto_X.Geometry[g].Center[2], 8)]
				# Radio
				Lista_Obj[t][1] = round(Boceto_X.Geometry[g].Radius, 8)
				# Punto inicio
				Lista_Obj[t][2] = Pt1_temp
				# Punto final
				Lista_Obj[t][3] = Pt2_temp
				# Centro curva
				Lista_Obj[t][4] = Eje_temp
			if Lista_Obj[t][5] == 'circulo':
				Eje_temp = [round(Boceto_X.Geometry[g].Center[0], 8), round(Boceto_X.Geometry[g].Center[1], 8), round(Boceto_X.Geometry[g].Center[2], 8)]
				# Radio
				Lista_Obj[t][1] = round(Boceto_X.Geometry[g].Radius, 8)
				# Centro curva
				Lista_Obj[t][4] = Eje_temp
			if Lista_Obj[t][5] == 'punto':
				Pt1_temp = [round(Boceto_X.Geometry[g].X, 8), round(Boceto_X.Geometry[g].Y, 8), round(Boceto_X.Geometry[g].Z, 8)]
				# Punto inicio
				Lista_Obj[t][2] = Pt1_temp
				
				
				
def Actualizar_Lista2(Boceto_X):
	
	Memo = []
	
	if len(Boceto_X.ExpressionEngine) > 0:
		for k in Boceto_X.ExpressionEngine:
			Memo.append(list(k))
	else:
		Memo.append([0, 0])
	
	for i, Data in enumerate(Boceto_X.Constraints):
		if Data.Name == '':
			Nom = '-'
			for m in Memo:
				if 'Constraints[' + str(i) + ']' == m[0]:
					Formula = m[1]
					break
				else:
					Formula = '-'
		else:
			Nom = Data.Name
			for n in Memo:
				if '.Constraints.' + Nom == n[0]:
					Formula = n[1]
					break
				else:
					Formula = '-'
		
		Grupo =  Lista_Obj[len(Lista_Obj) - len(Boceto_X.Geometry) + Data.First][7]
		Boceto = Lista_Obj[len(Lista_Obj) - len(Boceto_X.Geometry) + Data.First][6]
		
		Lista_Res.append([i])
		Lista_Res[-1].append(Data.Type)
		Lista_Res[-1].append(Nom)
		Lista_Res[-1].append(Data.Value)
		Lista_Res[-1].append(Grupo)
		Lista_Res[-1].append(Boceto)
		Lista_Res[-1].append(Formula)
		
		'''
		Lista_Res[-1].append(str(Data).split('\'')[0])			#N/A
		Lista_Res[-1].append(str(Data).split('\'')[1])			#Obj
		Lista_Res[-1].append(str(Data).split('\'')[2])			#N/A
		Lista_Res[-1].append(str(Data.Content).split(' ')[0])	#N/A
		Lista_Res[-1].append(str(Data.Content).split(' ')[1])	#.Name
		Lista_Res[-1].append(str(Data.Content).split(' ')[2])	#.Type
		Lista_Res[-1].append(str(Data.Content).split(' ')[3])	#.Value
		Lista_Res[-1].append(str(Data.Content).split(' ')[4])	#.LabelDistance
		Lista_Res[-1].append(str(Data.Content).split(' ')[5])	#.LabelPosition
		Lista_Res[-1].append(str(Data.Content).split(' ')[6])	#.IsDriving
		Lista_Res[-1].append(str(Data.Content).split(' ')[7])	#.IsInVirtualSpace
		Lista_Res[-1].append(str(Data.Content).split(' ')[8])	#.IsVisible
		Lista_Res[-1].append(str(Data.Content).split(' ')[9])	#.IsActive
		Lista_Res[-1].append(str(Data.Content).split(' ')[10])	#.First
		Lista_Res[-1].append(str(Data.Content).split(' ')[11])	#.FirstPos
		Lista_Res[-1].append(str(Data.Content).split(' ')[12])	#.Second
		Lista_Res[-1].append(str(Data.Content).split(' ')[13])	#.SecondPos
		Lista_Res[-1].append(str(Data.Content).split(' ')[14])	#.Third
		Lista_Res[-1].append(str(Data.Content).split(' ')[15])	#.ThirdPos
		Lista_Res[-1].append(str(Data.Content).split(' ')[16])	#.ElementIds
		Lista_Res[-1].append(str(Data.Content).split(' ')[17])	#.ElementIds[1]
		Lista_Res[-1].append(str(Data.Content).split(' ')[18])	#.ElementIds[2]
		Lista_Res[-1].append(str(Data.Content).split(' ')[19])	#.ElementPositions
		Lista_Res[-1].append(str(Data.Content).split(' ')[20])	#.ElementPositions[1]
		Lista_Res[-1].append(str(Data.Content).split(' ')[21])	#.ElementPositions[2]
		Lista_Res[-1].append(str(Data.Content).split(' ')[22])	#N/A
		'''
	
	
	
#! crear Bastidor 3D
def Crear_Bastidor_3D():
	
	### iniciar la orden PartDesign_Sketch
	global Boceto_Base
	# Crear_Boceto(Titulo, Etiqueta = '', Objeto_X = False, Plano_X = '', Modelado_X = '', Mapa_X = 'FlatFace'):
	Boceto_Base = Crear_Boceto('Sketch_Base_B001', 'B_Base_B001', Cuerpo_B1, 'XZ_Plane')
	
	# creamos la lista de puntos por cada linea
	geoList = []
	# [Punto inicial, Punto final]
	geoList.append([App.Vector(-278, 19, 0), App.Vector(-151, 19, 0)])		#Object[0]
	geoList.append([App.Vector(-146, 17, 0), App.Vector(-131,  2, 0)])		#Object[1]
	geoList.append([App.Vector(-127,  0, 0), App.Vector( 127,  0, 0)])		#Object[2]
	geoList.append([App.Vector( 131,  2, 0), App.Vector( 146, 17, 0)])		#Object[3]
	geoList.append([App.Vector( 151, 19, 0), App.Vector( 278, 19, 0)])		#Object[4]
	
	for NewLinea in geoList:
		# Crear_Linea(Pt1, Pt2, Boceto_X, Guia = False, Grupo_X = '-'):
		Crear_Linea(NewLinea[0], NewLinea[1], Boceto_Base)
	
	del geoList
	
	# creamos la lista de puntos por cada arco
	geoList = []
	# [centro curva, Eje, Radio, Angulo inicial, Angulo final]
	geoList.append([App.Vector(-151, 12, 0), App.Vector(0, 0, 1), 6.35, math.radians( 45), math.radians( 90)])	#Object[5]
	geoList.append([App.Vector(-127,  6, 0), App.Vector(0, 0, 1), 6.35, math.radians(225), math.radians(270)])	#Object[6]
	geoList.append([App.Vector( 127,  6, 0), App.Vector(0, 0, 1), 6.35, math.radians(270), math.radians(315)])	#Object[7]
	geoList.append([App.Vector( 151, 12, 0), App.Vector(0, 0, 1), 6.35, math.radians( 90), math.radians(135)])	#Object[8]
	
	for NewArco in geoList:
		# Crear_Arco(Pt1, Eje, Radio, Boceto_X, Ang_Ini, Ang_Fin, Guia = False, Grupo_X = '-'):
		Crear_Arco(NewArco[0], NewArco[1], NewArco[2], Boceto_Base, NewArco[3], NewArco[4])
	
	del geoList
	
	# creamos la lista de restricciones
	constraintList = []
	constraintList.append(Sketcher.Constraint('Tangent',    0,2,5,2))					#Constraints[0]
	constraintList.append(Sketcher.Constraint('Tangent',    1,1,5,1))					#Constraints[1]
	constraintList.append(Sketcher.Constraint('Tangent',    1,2,6,1))					#Constraints[2]
	constraintList.append(Sketcher.Constraint('Tangent',    2,1,6,2))					#Constraints[3]
	constraintList.append(Sketcher.Constraint('Tangent',    2,2,7,1))					#Constraints[4]
	constraintList.append(Sketcher.Constraint('Tangent',    3,1,7,2))					#Constraints[5]
	constraintList.append(Sketcher.Constraint('Tangent',    3,2,8,2))					#Constraints[6]
	constraintList.append(Sketcher.Constraint('Tangent',    4,1,8,1))					#Constraints[7]
	constraintList.append(Sketcher.Constraint('Horizontal', 0))							#Constraints[8]
	constraintList.append(Sketcher.Constraint('Horizontal', 2))							#Constraints[9]
	constraintList.append(Sketcher.Constraint('Horizontal', 4))							#Constraints[10]
	constraintList.append(Sketcher.Constraint('Symmetric',  2,1,2,2,-1,1))				#Constraints[11]
	constraintList.append(Sketcher.Constraint('Symmetric',  0,1,4,2,-2))					#Constraints[12]
	constraintList.append(Sketcher.Constraint('DistanceX',  2,1,2,2,241.0))				#Constraints[13]
	constraintList.append(Sketcher.Constraint('Radius',     5,6.35))						#Constraints[14]
	constraintList.append(Sketcher.Constraint('Radius',     6,6.35))						#Constraints[15]
	constraintList.append(Sketcher.Constraint('Radius',     7,6.35))						#Constraints[16]
	constraintList.append(Sketcher.Constraint('Radius',     8,6.35))						#Constraints[17]
	constraintList.append(Sketcher.Constraint('Angle',      0,2,1,1,math.radians(135)))	#Constraints[18]
	constraintList.append(Sketcher.Constraint('Angle',      3,2,4,1,math.radians(135)))	#Constraints[19]
	constraintList.append(Sketcher.Constraint('DistanceY',  2,1,0,1,19.0))				#Constraints[20]
	constraintList.append(Sketcher.Constraint('DistanceX',  0,1,4,2,508.0))				#Constraints[21]
	
	Boceto_Base.addConstraint(constraintList)
	Boceto_Base.setExpression('Constraints[20]', u'' + Variable_B1.Name + '.Alto')
	Boceto_Base.setExpression('Constraints[21]', u'' + Variable_B1.Name + '.Largo')
	Boceto_Base.renameConstraint(13, u'' + Pieza_B1.Name + '_Base')
	Boceto_Base.renameConstraint(20, u'' + Pieza_B1.Name + '_Alto')
	Boceto_Base.renameConstraint(21, u'' + Pieza_B1.Name + '_Largo')
	
	del constraintList
	
	# creamos la lista de puntos por cada linea
	geoList = []
	# [Punto inicial, Punto final]
	geoList.append([App.Vector(-247, 19, 0), App.Vector(-247, 16, 0)])		#Object[9]
	geoList.append([App.Vector(-247, 16, 0), App.Vector(-144, 16, 0)])		#Object[10]
	geoList.append([App.Vector(-140, 14, 0), App.Vector(-128,  0, 0)])		#Object[11]
	geoList.append([App.Vector(-120, -3, 0), App.Vector( 120, -3, 0)])		#Object[12]
	geoList.append([App.Vector( 128,  0, 0), App.Vector( 140, 14, 0)])		#Object[13]
	geoList.append([App.Vector( 144, 16, 0), App.Vector( 247, 16, 0)])		#Object[14]
	geoList.append([App.Vector( 247, 16, 0), App.Vector( 247, 19, 0)])		#Object[15]
	
	for NewLinea in geoList:
		# Crear_Linea(Pt1, Pt2, Boceto_X, Guia = False, Grupo_X = '-'):
		Crear_Linea(NewLinea[0], NewLinea[1], Boceto_Base)
	
	del geoList
	
	# creamos la lista de puntos por cada arco
	geoList = []
	# [centro curva, Eje, Radio, Angulo inicial, Angulo final]
	geoList.append([App.Vector(-144, 12, 0), App.Vector(0, 0, 1), 3.35, math.radians( 45), math.radians( 90)])	#Object[16]
	geoList.append([App.Vector(-120,  6, 0), App.Vector(0, 0, 1), 9.35, math.radians(225), math.radians(270)])	#Object[17]
	geoList.append([App.Vector( 120,  6, 0), App.Vector(0, 0, 1), 9.35, math.radians(270), math.radians(315)])	#Object[18]
	geoList.append([App.Vector( 144, 12, 0), App.Vector(0, 0, 1), 3.35, math.radians( 90), math.radians(135)])	#Object[19]
	
	for NewArco in geoList:
		# Crear_Arco(Pt1, Eje, Radio, Boceto_X, Ang_Ini, Ang_Fin, Guia = False, Grupo_X = '-'):
		Crear_Arco(NewArco[0], NewArco[1], NewArco[2], Boceto_Base, NewArco[3], NewArco[4])
	
	del geoList
	
	# creamos la lista de restricciones
	constraintList = []
	constraintList.append(Sketcher.Constraint('Coincident', 9,1,0,1))		#Constraints[22]
	constraintList.append(Sketcher.Constraint('Coincident', 9,2,10,1))		#Constraints[23]
	constraintList.append(Sketcher.Constraint('Coincident', 5,3,16,3))		#Constraints[24]
	constraintList.append(Sketcher.Constraint('Coincident', 6,3,17,3))		#Constraints[25]
	constraintList.append(Sketcher.Constraint('Coincident', 7,3,18,3))		#Constraints[26]
	constraintList.append(Sketcher.Constraint('Coincident', 8,3,19,3))		#Constraints[27]
	constraintList.append(Sketcher.Constraint('Coincident', 15,2,4,2))		#Constraints[28]
	constraintList.append(Sketcher.Constraint('Coincident', 14,2,15,1))		#Constraints[29]
	constraintList.append(Sketcher.Constraint('Tangent',    10,2,16,2))		#Constraints[30]
	constraintList.append(Sketcher.Constraint('Tangent',    11,1,16,1))		#Constraints[31]
	constraintList.append(Sketcher.Constraint('Tangent',    11,2,17,1))		#Constraints[32]
	constraintList.append(Sketcher.Constraint('Tangent',    12,1,17,2))		#Constraints[33]
	constraintList.append(Sketcher.Constraint('Tangent',    12,2,18,1))		#Constraints[34]
	constraintList.append(Sketcher.Constraint('Tangent',    13,1,18,2))		#Constraints[35]
	constraintList.append(Sketcher.Constraint('Tangent',    13,2,19,2))		#Constraints[36]
	constraintList.append(Sketcher.Constraint('Tangent',    14,1,19,1))		#Constraints[37]
	constraintList.append(Sketcher.Constraint('Parallel',   11,1))			#Constraints[38]
	constraintList.append(Sketcher.Constraint('Parallel',   13,3))			#Constraints[39]
	constraintList.append(Sketcher.Constraint('Vertical',   9))				#Constraints[40]
	constraintList.append(Sketcher.Constraint('Horizontal', 10))				#Constraints[41]
	constraintList.append(Sketcher.Constraint('Horizontal', 12))				#Constraints[42]
	constraintList.append(Sketcher.Constraint('Horizontal', 14))				#Constraints[43]
	constraintList.append(Sketcher.Constraint('Vertical',   15))				#Constraints[44]
	constraintList.append(Sketcher.Constraint('DistanceY',  14,2,4,2,2.0))	#Constraints[45]
	
	Boceto_Base.addConstraint(constraintList)
	Boceto_Base.setExpression('Constraints[45]', u'' + Variable_B1.Name + '.Espesor')
	Boceto_Base.renameConstraint(45, u'' + Pieza_B1.Name + '_Espesor')
	
	del constraintList
	
	Doc.recompute()
	
	# Actualizar_Lista(Boceto_X):
	Actualizar_Lista(Boceto_Base)
	Actualizar_Lista2(Boceto_Base)
	
	global Relleno_Base
	# Crear_Relleno(Titulo, Etiqueta = '', Objeto_X = False, Boceto_X = False):
	Relleno_Base = Crear_Relleno('Pad_Base_B001', 'Relleno_Base_B001', Cuerpo_B1, Boceto_Base)
	Relleno_Base.setExpression('Length', u'' + Variable_B1.Name + '.Ancho')
	Relleno_Base.SideType = 2
	
	Doc.recompute()
	
	
	
#! Crear Huecos en el Bastidor
def Crear_Huecos01_3D(LaT, AnT, AlT):
	
	### iniciar la orden PartDesign_Sketch
	global Boceto_Hueco1
	# Crear_Boceto(Titulo, Etiqueta = '', Objeto_X = False, Plano_X = '', Modelado_X = '', Mapa_X = 'FlatFace'):
	Boceto_Hueco1 = Crear_Boceto('Sketch_HuecoBase1_B001', 'B_HuecoBase1_B001', Cuerpo_B1, 'Face5', Relleno_Base)
	
	# Crear_Cuadrado(Pt1, Boceto_X, Tipo = 'Borde', Dist_X = False, Dist_Y = False, Radio = False, Angulo = 0, Guia = False, Grupo = '-'):
	Crear_Cuadrado(App.Vector(0, 0, 0), Boceto_Hueco1, 'Borde', 177.8, AnT - 38.1, 3, Grupo = 'CB1_C')
	Boceto_Hueco1.setExpression('Constraints[24]', u'' + Variable_B1.Name + '.Ancho - 38.1 mm')
	Boceto_Hueco1.renameConstraint(24, u'' + Pieza_B1.Name + '_HB1-C_Y')
	
	# Crear_Cuadrado(Pt1, Boceto_X, Tipo = 'Borde', Dist_X = False, Dist_Y = False, Radio = False, Angulo = 0, Guia = False, Grupo = '-'):
	Crear_Cuadrado(App.Vector(177.8 / 2 + 5 + 10 / 2, 0, 0), Boceto_Hueco1, 'Borde', 10, AnT - 38.1, 3, Grupo = 'CB2_D')
	Boceto_Hueco1.setExpression('Constraints[59]', u'' + Variable_B1.Name + '.Ancho - 38.1 mm')
	Boceto_Hueco1.renameConstraint(59, u'' + Pieza_B1.Name + '_HB1-D_Y')
	
	# Crear_Cuadrado(Pt1, Boceto_X, Tipo = 'Borde', Dist_X = False, Dist_Y = False, Radio = False, Angulo = 0, Guia = False, Grupo = '-'):
	Crear_Cuadrado(App.Vector(-177.8 / 2 - 5 - 10 / 2, 0, 0), Boceto_Hueco1, 'Borde', 10, AnT - 38.1, 3, Grupo = 'CB3_I')
	Boceto_Hueco1.setExpression('Constraints[94]', u'' + Variable_B1.Name + '.Ancho - 38.1 mm')
	Boceto_Hueco1.renameConstraint(94, u'' + Pieza_B1.Name + '_HB1-I_Y')
	
	Doc.recompute()
	
	# Actualizar_Lista(Boceto_X):
	Actualizar_Lista(Boceto_Hueco1)
	Actualizar_Lista2(Boceto_Hueco1)
	
	global Hueco_Base1
	# Crear_Hueco(Titulo, Etiqueta = '', Objeto_X = False, Boceto_X = False):
	Hueco_Base1 = Crear_Hueco('Pocket_Base1_B001', 'Hueco_Base1_B001', Cuerpo_B1, Boceto_Hueco1)
	
	Doc.recompute()
	
	
	
def Crear_Huecos02_3D(LaT, AnT, AlT):
	
	### iniciar la orden PartDesign_Sketch
	global Boceto_Hueco2
	# Crear_Boceto(Titulo, Etiqueta = '', Objeto_X = False, Plano_X = '', Modelado_X = '', Mapa_X = 'FlatFace'):
	Boceto_Hueco2 = Crear_Boceto('Sketch_HuecoBase2_B001', 'B_HuecoBase2_B001', Cuerpo_B1, 'Face1', Hueco_Base1)
	'''
	# Crear_Ranura(Pt1, Boceto_X, Dist_X = False, Dist_Y = False, Angulo = 0, Guia = False, Grupo = '-'):
	Crear_Ranura(App.Vector(-LaT / 2 + 2.5 + 12.7 / 2, -AnT / 2 + 8 + 6.35 / 2, 0), Boceto_Hueco2, 12.7, 6.35, Grupo = 'Ra1')
	Boceto_Hueco2.setExpression('Constraints[41]', u'-' + Variable_B1.Name + '.Largo / 2 + ' + str(2.5 + 12.7 / 2) + ' mm')
	Boceto_Hueco2.setExpression('Constraints[42]', u'-' + Variable_B1.Name + '.Ancho / 2 + ' + str(8 + 6.35 / 2) + ' mm')
	Boceto_Hueco2.renameConstraint(41, u'' + Pieza_B1.Name + '_H2-Ra1_X')
	Boceto_Hueco2.renameConstraint(42, u'' + Pieza_B1.Name + '_H2-Ra1_Y')
	
	# Crear_Cuadrado(Pt1, Boceto_X, Tipo = 'Borde', Dist_X = False, Dist_Y = False, Radio = False, Angulo = 0, Guia = False, Grupo = '-'):
	Crear_Cuadrado(App.Vector(-LaT / 2 + 2.5 + 12.7 / 2, -AnT / 2 + 8 + 6.35 + 5 + 6.35 / 2, 0), Boceto_Hueco2, 'Esquina', 12.7, 6.35, Grupo = 'C1')
	Boceto_Hueco2.setExpression('Constraints[60]', u'-' + Variable_B1.Name + '.Largo / 2 + ' + str(2.5 + 12.7 / 2) + ' mm')
	Boceto_Hueco2.setExpression('Constraints[61]', u'-' + Variable_B1.Name + '.Ancho / 2 + ' + str(8 + 6.35 + 5 + 6.35 / 2) + ' mm')
	Boceto_Hueco2.renameConstraint(60, u'' + Pieza_B1.Name + '_H2-C1_X')
	Boceto_Hueco2.renameConstraint(61, u'' + Pieza_B1.Name + '_H2-C1_Y')
	
	# Crear_Semicirculo(Pt1, Boceto_X, Dist_X = False, Dist_Y = False, Tipo = 'B', Angulo = 0, Radio_Centro = False, Guia = False, Grupo = '-'):
	m = 2 * 6.35 * math.sin(math.radians(45))
	n = AlT - 2 * (6.35 - 6.35 * math.cos(math.radians(45)))
	Crear_Semicirculo(App.Vector(-241 / 2 - m - n - 5,      -AnT / 2 + 26,      0), Boceto_Hueco2, 10, 12, 'B', Grupo = 'SC1')
	Crear_Semicirculo(App.Vector(-241 / 2 - m - n - 5,       AnT / 2 - 26,      0), Boceto_Hueco2, 10, 12, 'B', math.radians(180), Grupo = 'SC2')
	Crear_Semicirculo(App.Vector(-241 / 2 - m - n - 5 - 20, -AnT / 2 + 26 - 10, 0), Boceto_Hueco2, 10, 12, 'B', math.radians(90),  Grupo = 'SC3')
	Crear_Semicirculo(App.Vector(-241 / 2 - m - n - 5 - 20,  AnT / 2 - 26 + 10, 0), Boceto_Hueco2, 10, 12, 'B', math.radians(90),  Grupo = 'SC4')
	Boceto_Hueco2.setExpression('Constraints[94]', u'-' + Variable_B1.Name + '.Ancho / 2 + 26 mm')
	Boceto_Hueco2.renameConstraint(94, u'' + Pieza_B1.Name + '_H2-SC1_Y')
	Boceto_Hueco2.setExpression('Constraints[127]', u'' + Variable_B1.Name + '.Ancho / 2 - 26 mm')
	Boceto_Hueco2.renameConstraint(127, u'' + Pieza_B1.Name + '_H2-SC2_Y')
	Boceto_Hueco2.setExpression('Constraints[160]', u'-' + Variable_B1.Name + '.Ancho / 2 + 16 mm')
	Boceto_Hueco2.renameConstraint(160, u'' + Pieza_B1.Name + '_H2-SC3_Y')
	Boceto_Hueco2.setExpression('Constraints[193]', u'' + Variable_B1.Name + '.Ancho / 2 - 16 mm')
	Boceto_Hueco2.renameConstraint(193, u'' + Pieza_B1.Name + '_H2-SC4_Y')
	
	Doc.recompute()
	'''
	
	# Crear_Estrella(Pt1, Boceto_X, Radio1, Radio2, Puntas = 5, Angulo = 0, Tipo = 'TA', Radio3 = 5, Angulo2 = 36, Grupo = '-'):
	#Crear_Estrella(App.Vector(-200, 10, 0), Boceto_Hueco2, 20, 15, 4, math.radians(30), 'TB', 5, math.radians(90), Grupo = 'Estrella1')
	#Crear_Estrella(App.Vector(-200, -25, 0), Boceto_Hueco2, 10, 5, 4, math.radians(90), 'TA', Grupo = 'Estrella2')
	
	# Crear_Keyhole(Pt1, Boceto_X, Radio1, Radio2, Largo, Angulo = 0, Tipo = 'TA', Grupo = '-'):
	Crear_Keyhole(App.Vector(-200, -10, 0), Boceto_Hueco2, 5, 15, 50, math.radians(90), 'TB')
	
	# Actualizar_Lista(Boceto_X):
	Actualizar_Lista(Boceto_Hueco2)
	Actualizar_Lista2(Boceto_Hueco2)
	
	global Hueco_Base2
	# Crear_Hueco(Titulo, Etiqueta = '', Objeto_X = False, Boceto_X = False):
	Hueco_Base2 = Crear_Hueco('Pocket_Base2_B001', 'Hueco_Base2_B001', Cuerpo_B1, Boceto_Hueco2)
	
	Doc.recompute()
	'''
	# Crear_LineaRef(Titulo, Etiqueta = '', Objeto_X = False, Eje_X = '', Modelado_X = ''):
	global DL1
	global DL2
	global DL3
	global DL4
	DL1 = Crear_LineaRef('DL1_Base2_B001', 'LinRef1_Base2_B001', Cuerpo_B1, 'Edge71',  Hueco_Base2)
	DL2 = Crear_LineaRef('DL2_Base2_B001', 'LinRef2_Base2_B001', Cuerpo_B1, 'Edge59',  Hueco_Base2)
	DL3 = Crear_LineaRef('DL3_Base2_B001', 'LinRef3_Base2_B001', Cuerpo_B1, 'Edge119', Hueco_Base2)
	DL4 = Crear_LineaRef('DL4_Base2_B001', 'LinRef4_Base2_B001', Cuerpo_B1, 'Edge111', Hueco_Base2)
	DL1.AttachmentOffset = App.Placement(App.Vector(0, -1, -241 / 2 - m - n - 10), App.Rotation(0, 0, 0))
	DL2.AttachmentOffset = App.Placement(App.Vector(0, -1,  241 / 2 + m + n),      App.Rotation(0, 0, 0))
	DL3.AttachmentOffset = App.Placement(App.Vector(0, -1,  AnT / 2 - 26 + 5),     App.Rotation(0, 0, 0))
	DL4.AttachmentOffset = App.Placement(App.Vector(0, -1, -AnT / 2 + 26 - 15),    App.Rotation(0, 0, 0))
	
	Doc.recompute()
	'''
	
	
def Crear_Huecos03_3D(LaT, AnT, AlT):
	
	### iniciar la orden PartDesign_Sketch
	global Boceto_Hueco3
	# Crear_Boceto(Titulo, Etiqueta = '', Objeto_X = False, Plano_X = '', Modelado_X = '', Mapa_X = 'FlatFace'):
	Boceto_Hueco3 = Crear_Boceto('Sketch_HuecoBase3_B001', 'B_HuecoBase3_B001', Cuerpo_B1, 'Face34', Hueco_Base2)
	
	# Crear_Cuadrado(Pt1, Boceto_X, Tipo = 'Borde', Dist_X = False, Dist_Y = False, Radio = False, Angulo = 0, Guia = False, Grupo = '-'):
	Crear_Cuadrado(App.Vector(LaT / 2 - 2.5 - 12.7 / 2, -AnT / 2 + 8 + 6.35 + 5 + 6.35 / 2, 0), Boceto_Hueco3, 'Esquina', 12.7, 6.35, Grupo = 'C1')
	Boceto_Hueco3.setExpression('Constraints[17]', u'' + Variable_B1.Name + '.Largo / 2 - ' + str(2.5 + 12.7 / 2) + ' mm')
	Boceto_Hueco3.setExpression('Constraints[18]', u'-' + Variable_B1.Name + '.Ancho / 2 + ' + str(8 + 6.35 + 5 + 6.35 / 2) + ' mm')
	Boceto_Hueco3.renameConstraint(17, u'' + Pieza_B1.Name + '_H3-C1_X')
	Boceto_Hueco3.renameConstraint(18, u'' + Pieza_B1.Name + '_H3-C1_Y')
	
	# Crear_Circulo(Pt1, Eje, Radio, Boceto_X, Guia = False, Grupo_X = '-'):
	Cir1 = Crear_Circulo(App.Vector(LaT / 2 - 2.5 - 12.7 / 2, -AnT / 2 + 8 + 6.35 / 2, 0), App.Vector(0, 0, 1), 2.5, Boceto_Hueco3, Grupo_X = 'Cir2')
	Boceto_Hueco3.addConstraint(Sketcher.Constraint('Radius',    len(Boceto_Hueco3.Geometry) - 1, 2.5))
	Boceto_Hueco3.addConstraint(Sketcher.Constraint('DistanceX', len(Boceto_Hueco3.Geometry) - 1, 3, LaT / 2 - 2.5 - 12.7 / 2))
	Boceto_Hueco3.addConstraint(Sketcher.Constraint('DistanceY', len(Boceto_Hueco3.Geometry) - 1, 3, -AnT / 2 + 8 + 6.35 / 2))
	Boceto_Hueco3.setExpression('Constraints[20]', u'' + Variable_B1.Name + '.Largo / 2 - ' + str(2.5 + 12.7 / 2) + ' mm')
	Boceto_Hueco3.setExpression('Constraints[21]', u'-' + Variable_B1.Name + '.Ancho / 2 + ' + str(8 + 6.35 / 2) + ' mm')
	Boceto_Hueco3.renameConstraint(20, u'' + Pieza_B1.Name + '_H3-Cir2_X')
	Boceto_Hueco3.renameConstraint(21, u'' + Pieza_B1.Name + '_H3-Cir2_Y')
	
	# Crear_Semicirculo(Pt1, Boceto_X, Dist_X = False, Dist_Y = False, Tipo = 'B', Angulo = 0, Radio_Centro = False, Guia = False, Grupo = '-'):
	m = 2 * 6.35 * math.sin(math.radians(45))
	n = AlT - 2 * (6.35 - 6.35 * math.cos(math.radians(45)))
	Crear_Semicirculo(App.Vector(241 / 2 + m + n + 5,      -AnT / 2 + 26,      0), Boceto_Hueco3, 10, 12, 'B', Grupo = 'SC1')
	Crear_Semicirculo(App.Vector(241 / 2 + m + n + 5,       AnT / 2 - 26,      0), Boceto_Hueco3, 10, 12, 'B', math.radians(180), Grupo = 'SC2')
	Crear_Semicirculo(App.Vector(LaT / 2 - 2.5 - 12.7 / 2,  AnT / 2 - 5,       0), Boceto_Hueco3,  8, 10, 'B', math.radians(180), Grupo = 'SC3')
	Crear_Semicirculo(App.Vector(241 / 2 + m + n + 5 + 20, -AnT / 2 + 26 - 10, 0), Boceto_Hueco3, 10, 12, 'B', math.radians(270), Grupo = 'SC4')
	Crear_Semicirculo(App.Vector(241 / 2 + m + n + 5 + 20,  AnT / 2 - 26 + 10, 0), Boceto_Hueco3, 10, 12, 'B', math.radians(270), Grupo = 'SC5')
	Boceto_Hueco3.setExpression('Constraints[54]', u'-' + Variable_B1.Name + '.Ancho / 2 + 26 mm')
	Boceto_Hueco3.renameConstraint(54, u'' + Pieza_B1.Name + '_H3-SC1_Y')
	Boceto_Hueco3.setExpression('Constraints[87]', u'' + Variable_B1.Name + '.Ancho / 2 - 26 mm')
	Boceto_Hueco3.renameConstraint(87, u'' + Pieza_B1.Name + '_H3-SC2_Y')
	Boceto_Hueco3.setExpression('Constraints[119]', u'' + Variable_B1.Name + '.Largo / 2 - ' + str(2.5 + 12.7 / 2) + ' mm')
	Boceto_Hueco3.setExpression('Constraints[120]', u'' + Variable_B1.Name + '.Ancho / 2 - 5 mm')
	Boceto_Hueco3.renameConstraint(119, u'' + Pieza_B1.Name + '_H3-SC3_X')
	Boceto_Hueco3.renameConstraint(120, u'' + Pieza_B1.Name + '_H3-SC3_Y')
	Boceto_Hueco3.setExpression('Constraints[153]', u'-' + Variable_B1.Name + '.Ancho / 2 + 16 mm')
	Boceto_Hueco3.renameConstraint(153, u'' + Pieza_B1.Name + '_H3-SC4_Y')
	Boceto_Hueco3.setExpression('Constraints[186]', u'' + Variable_B1.Name + '.Ancho / 2 - 16 mm')
	Boceto_Hueco3.renameConstraint(186, u'' + Pieza_B1.Name + '_H3-SC5_Y')
	
	Doc.recompute()
	
	# Actualizar_Lista(Boceto_X):
	Actualizar_Lista(Boceto_Hueco3)
	Actualizar_Lista2(Boceto_Hueco3)
	
	global Hueco_Base3
	# Crear_Hueco(Titulo, Etiqueta = '', Objeto_X = False, Boceto_X = False):
	Hueco_Base3 = Crear_Hueco('Pocket_Base3_B001', 'Hueco_Base3_B001', Cuerpo_B1, Boceto_Hueco3)
	
	Doc.recompute()
	
	# Crear_LineaRef(Titulo, Etiqueta = '', Objeto_X = False, Eje_X = '', Modelado_X = ''):
	global DL5
	global DL6
	global DL7
	global DL8
	DL5 = Crear_LineaRef('DL5_Base3_B001', 'LinRef5_Base3_B001', Cuerpo_B1, 'Edge173', Hueco_Base3)
	DL6 = Crear_LineaRef('DL6_Base3_B001', 'LinRef6_Base3_B001', Cuerpo_B1, 'Edge168', Hueco_Base3)
	DL7 = Crear_LineaRef('DL7_Base3_B001', 'LinRef7_Base3_B001', Cuerpo_B1, 'Edge184', Hueco_Base3)
	DL8 = Crear_LineaRef('DL8_Base3_B001', 'LinRef8_Base3_B001', Cuerpo_B1, 'Edge175', Hueco_Base3)
	DL5.AttachmentOffset = App.Placement(App.Vector(0, -1, -241 / 2 - m - n - 10), App.Rotation(0, 0, 0))
	DL6.AttachmentOffset = App.Placement(App.Vector(0, -1,  241 / 2 + m + n),      App.Rotation(0, 0, 0))
	DL7.AttachmentOffset = App.Placement(App.Vector(0, -1,  AnT / 2 - 26 + 5),     App.Rotation(0, 0, 0))
	DL8.AttachmentOffset = App.Placement(App.Vector(0, -1, -AnT / 2 + 26 - 15),    App.Rotation(0, 0, 0))
	
	Doc.recompute()
	
	
	
def Crear_Doblez01():
	
	### iniciar la orden PartDesign_Sketch
	global Boceto_Doblez1
	# Crear_Boceto(Titulo, Etiqueta = '', Objeto_X = False, Plano_X = '', Modelado_X = '', Mapa_X = 'FlatFace'):
	Boceto_Doblez1 = Crear_Boceto('Sketch_Fold1_B001', 'B_Doblez1_B001', Cuerpo_B1, 'Face9', Hueco_Base3, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez1, 'Esquina', Var_E, 9)
	
	Doc.recompute()
	
	# Actualizar_Lista(Boceto_X):
	Actualizar_Lista(Boceto_Doblez1)
	Actualizar_Lista2(Boceto_Doblez1)
	
	global Doblez1_Base2
	# Crear_Revolucion(Titulo, Etiqueta = '', Objeto_X = False, Boceto_X = False, Eje_X = False, Angulo = 360, Reverso = 0):
	Doblez1_Base2 = Crear_Revolucion('Rev_Hole1_B001', 'Rev_Hueco1_B001', Cuerpo_B1, Boceto_Doblez1, DL1, 90, 1)
	
	Doc.recompute()
	
	# Crear_PlanoRef(Titulo, Etiqueta = '', Objeto_X = False, Eje_X = '', Modelado_X = ''):
	global DP1
	DP1 = Crear_PlanoRef('DP1_Base2_B001', 'PlanRef1_Base2_B001', Cuerpo_B1, 'Edge264',  Doblez1_Base2)
	DP1.AttachmentOffset = App.Placement(App.Vector(0, 0, -4.5), App.Rotation(0, 90, 0))
	DP1.Visibility = False
	
	# Crear_Boceto(Titulo, Etiqueta = '', Objeto_X = False, Plano_X = '', Modelado_X = '', Mapa_X = 'FlatFace'):
	Boceto_Tab1 = Crear_Boceto('Sketch_Tab1_B001', 'B_Tab1_B001', Cuerpo_B1, Modelado_X = DP1)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab1, 9, 9, 'B', math.radians(180), 2)
	
	# Actualizar_Lista(Boceto_X):
	Actualizar_Lista(Boceto_Tab1)
	Actualizar_Lista2(Boceto_Tab1)
	
	global Tab1_Base2
	# Crear_Relleno(Titulo, Etiqueta = '', Objeto_X = False, Boceto_X = False):
	Tab1_Base2 = Crear_Relleno('Pad_Tab1_B001', 'Relleno_Tab1_B001', Cuerpo_B1, Boceto_Tab1)
	Tab1_Base2.setExpression('Length', u'' + Variable_B1.Name + '.Espesor')
	
	Doc.recompute()
	
	
	
def Crear_Doblez02():
	
	### iniciar la orden PartDesign_Sketch
	global Boceto_Doblez2
	# Crear_Boceto(Titulo, Etiqueta = '', Objeto_X = False, Plano_X = '', Modelado_X = '', Mapa_X = 'FlatFace'):
	Boceto_Doblez2 = Crear_Boceto('Sketch_Fold2_B001', 'B_Doblez2_B001', Cuerpo_B1, 'Face4', Tab1_Base2, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez2, 'Esquina', Var_E, 9)
	
	Doc.recompute()
	
	# Actualizar_Lista(Boceto_X):
	Actualizar_Lista(Boceto_Doblez2)
	Actualizar_Lista2(Boceto_Doblez2)
	
	global Doblez2_Base2
	# Crear_Revolucion(Titulo, Etiqueta = '', Objeto_X = False, Boceto_X = False, Eje_X = False, Angulo = 360, Reverso = 0):
	Doblez2_Base2 = Crear_Revolucion('Rev_Hole2_B001', 'Rev_Hueco2_B001', Cuerpo_B1, Boceto_Doblez2, DL2, 90, 1)
	
	Doc.recompute()
	
	# Crear_PlanoRef(Titulo, Etiqueta = '', Objeto_X = False, Eje_X = '', Modelado_X = ''):
	global DP2
	DP2 = Crear_PlanoRef('DP2_Base2_B001', 'PlanRef2_Base2_B001', Cuerpo_B1, 'Edge273',  Doblez2_Base2)
	DP2.AttachmentOffset = App.Placement(App.Vector(0, 0, -4.5), App.Rotation(0, 90, 0))
	DP2.Visibility = False
	
	# Crear_Boceto(Titulo, Etiqueta = '', Objeto_X = False, Plano_X = '', Modelado_X = '', Mapa_X = 'FlatFace'):
	Boceto_Tab2 = Crear_Boceto('Sketch_Tab2_B001', 'B_Tab2_B001', Cuerpo_B1, Modelado_X = DP2)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab2, 9, 9, 'B', math.radians(180), 2)
	
	# Actualizar_Lista(Boceto_X):
	Actualizar_Lista(Boceto_Tab2)
	Actualizar_Lista2(Boceto_Tab2)
	
	global Tab2_Base2
	# Crear_Relleno(Titulo, Etiqueta = '', Objeto_X = False, Boceto_X = False):
	Tab2_Base2 = Crear_Relleno('Pad_Tab2_B001', 'Relleno_Tab2_B001', Cuerpo_B1, Boceto_Tab2)
	Tab2_Base2.setExpression('Length', u'' + Variable_B1.Name + '.Espesor')
	Tab2_Base2.Reversed = 1
	
	Doc.recompute()
	
	
	
def Crear_Doblez03():
	
	### iniciar la orden PartDesign_Sketch
	global Boceto_Doblez3
	# Crear_Boceto(Titulo, Etiqueta = '', Objeto_X = False, Plano_X = '', Modelado_X = '', Mapa_X = 'FlatFace'):
	Boceto_Doblez3 = Crear_Boceto('Sketch_Fold3_B001', 'B_Doblez3_B001', Cuerpo_B1, 'Face29', Tab2_Base2, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez3, 'Esquina', Var_E, 9)
	
	Doc.recompute()
	
	# Actualizar_Lista(Boceto_X):
	Actualizar_Lista(Boceto_Doblez3)
	Actualizar_Lista2(Boceto_Doblez3)
	
	global Doblez3_Base2
	# Crear_Revolucion(Titulo, Etiqueta = '', Objeto_X = False, Boceto_X = False, Eje_X = False, Angulo = 360, Reverso = 0):
	Doblez3_Base2 = Crear_Revolucion('Rev_Hole3_B001', 'Rev_Hueco3_B001', Cuerpo_B1, Boceto_Doblez3, DL3, 90, 1)
	
	Doc.recompute()
	
	# Crear_PlanoRef(Titulo, Etiqueta = '', Objeto_X = False, Eje_X = '', Modelado_X = ''):
	global DP3
	DP3 = Crear_PlanoRef('DP3_Base2_B001', 'PlanRef3_Base2_B001', Cuerpo_B1, 'Edge305',  Doblez3_Base2)
	DP3.AttachmentOffset = App.Placement(App.Vector(0, 0, -4.5), App.Rotation(0, 90, 0))
	DP3.Visibility = False
	
	# Crear_Boceto(Titulo, Etiqueta = '', Objeto_X = False, Plano_X = '', Modelado_X = '', Mapa_X = 'FlatFace'):
	Boceto_Tab3 = Crear_Boceto('Sketch_Tab3_B001', 'B_Tab3_B001', Cuerpo_B1, Modelado_X = DP3)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab3, 9, 9, 'B', math.radians(180), 2)
	
	# Actualizar_Lista(Boceto_X):
	Actualizar_Lista(Boceto_Tab3)
	Actualizar_Lista2(Boceto_Tab3)
	
	global Tab3_Base2
	# Crear_Relleno(Titulo, Etiqueta = '', Objeto_X = False, Boceto_X = False):
	Tab3_Base2 = Crear_Relleno('Pad_Tab3_B001', 'Relleno_Tab3_B001', Cuerpo_B1, Boceto_Tab3)
	Tab3_Base2.setExpression('Length', u'' + Variable_B1.Name + '.Espesor')
	Tab3_Base2.Reversed = 1
	
	Doc.recompute()
	
	
	
def Crear_Doblez04():
	
	### iniciar la orden PartDesign_Sketch
	global Boceto_Doblez4
	# Crear_Boceto(Titulo, Etiqueta = '', Objeto_X = False, Plano_X = '', Modelado_X = '', Mapa_X = 'FlatFace'):
	Boceto_Doblez4 = Crear_Boceto('Sketch_Fold4_B001', 'B_Doblez4_B001', Cuerpo_B1, 'Face25', Tab3_Base2, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez4, 'Esquina', Var_E, 9)
	
	Doc.recompute()
	
	# Actualizar_Lista(Boceto_X):
	Actualizar_Lista(Boceto_Doblez4)
	Actualizar_Lista2(Boceto_Doblez4)
	
	global Doblez4_Base2
	# Crear_Revolucion(Titulo, Etiqueta = '', Objeto_X = False, Boceto_X = False, Eje_X = False, Angulo = 360, Reverso = 0):
	Doblez4_Base2 = Crear_Revolucion('Rev_Hole4_B001', 'Rev_Hueco4_B001', Cuerpo_B1, Boceto_Doblez4, DL4, 90, 1)
	
	Doc.recompute()
	
	# Crear_PlanoRef(Titulo, Etiqueta = '', Objeto_X = False, Eje_X = '', Modelado_X = ''):
	global DP4
	DP4 = Crear_PlanoRef('DP4_Base2_B001', 'PlanRef4_Base2_B001', Cuerpo_B1, 'Edge314',  Doblez4_Base2)
	DP4.AttachmentOffset = App.Placement(App.Vector(0, 0, -4.5), App.Rotation(0, 90, 0))
	DP4.Visibility = False
	
	# Crear_Boceto(Titulo, Etiqueta = '', Objeto_X = False, Plano_X = '', Modelado_X = '', Mapa_X = 'FlatFace'):
	Boceto_Tab4 = Crear_Boceto('Sketch_Tab4_B001', 'B_Tab4_B001', Cuerpo_B1, Modelado_X = DP4)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab4, 9, 9, 'B', math.radians(180), 2)
	
	# Actualizar_Lista(Boceto_X):
	Actualizar_Lista(Boceto_Tab4)
	Actualizar_Lista2(Boceto_Tab4)
	
	global Tab4_Base2
	# Crear_Relleno(Titulo, Etiqueta = '', Objeto_X = False, Boceto_X = False):
	Tab4_Base2 = Crear_Relleno('Pad_Tab4_B001', 'Relleno_Tab4_B001', Cuerpo_B1, Boceto_Tab4)
	Tab4_Base2.setExpression('Length', u'' + Variable_B1.Name + '.Espesor')
	Tab4_Base2.Reversed = 1
	
	Doc.recompute()
	
	
	
def Crear_Doblez05():
	
	### iniciar la orden PartDesign_Sketch
	global Boceto_Doblez5
	# Crear_Boceto(Titulo, Etiqueta = '', Objeto_X = False, Plano_X = '', Modelado_X = '', Mapa_X = 'FlatFace'):
	Boceto_Doblez5 = Crear_Boceto('Sketch_Fold5_B001', 'B_Doblez5_B001', Cuerpo_B1, 'Face104', Tab4_Base2, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez5, 'Esquina', Var_E, 9)
	
	Doc.recompute()
	
	# Actualizar_Lista(Boceto_X):
	Actualizar_Lista(Boceto_Doblez5)
	Actualizar_Lista2(Boceto_Doblez5)
	
	global Doblez5_Base3
	# Crear_Revolucion(Titulo, Etiqueta = '', Objeto_X = False, Boceto_X = False, Eje_X = False, Angulo = 360, Reverso = 0):
	Doblez5_Base3 = Crear_Revolucion('Rev_Hole5_B001', 'Rev_Hueco5_B001', Cuerpo_B1, Boceto_Doblez5, DL5, 90, 1)
	
	Doc.recompute()
	
	# Crear_PlanoRef(Titulo, Etiqueta = '', Objeto_X = False, Eje_X = '', Modelado_X = ''):
	global DP5
	DP5 = Crear_PlanoRef('DP5_Base3_B001', 'PlanRef5_Base3_B001', Cuerpo_B1, 'Edge377',  Doblez5_Base3)
	DP5.AttachmentOffset = App.Placement(App.Vector(0, 0, -4.5), App.Rotation(0, 90, 0))
	DP5.Visibility = False
	
	# Crear_Boceto(Titulo, Etiqueta = '', Objeto_X = False, Plano_X = '', Modelado_X = '', Mapa_X = 'FlatFace'):
	Boceto_Tab5 = Crear_Boceto('Sketch_Tab5_B001', 'B_Tab5_B001', Cuerpo_B1, Modelado_X = DP5)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab5, 9, 9, 'B', math.radians(180), 2)
	
	# Actualizar_Lista(Boceto_X):
	Actualizar_Lista(Boceto_Tab5)
	Actualizar_Lista2(Boceto_Tab5)
	
	global Tab5_Base3
	# Crear_Relleno(Titulo, Etiqueta = '', Objeto_X = False, Boceto_X = False):
	Tab5_Base3 = Crear_Relleno('Pad_Tab5_B001', 'Relleno_Tab5_B001', Cuerpo_B1, Boceto_Tab5)
	Tab5_Base3.setExpression('Length', u'' + Variable_B1.Name + '.Espesor')
	Tab5_Base3.Reversed = 1
	
	Doc.recompute()
	
	
	
def Crear_Doblez06():
	
	### iniciar la orden PartDesign_Sketch
	global Boceto_Doblez6
	# Crear_Boceto(Titulo, Etiqueta = '', Objeto_X = False, Plano_X = '', Modelado_X = '', Mapa_X = 'FlatFace'):
	Boceto_Doblez6 = Crear_Boceto('Sketch_Fold6_B001', 'B_Doblez6_B001', Cuerpo_B1, 'Face101', Tab5_Base3, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez6, 'Esquina', Var_E, 9)
	
	Doc.recompute()
	
	# Actualizar_Lista(Boceto_X):
	Actualizar_Lista(Boceto_Doblez6)
	Actualizar_Lista2(Boceto_Doblez6)
	
	global Doblez6_Base3
	# Crear_Revolucion(Titulo, Etiqueta = '', Objeto_X = False, Boceto_X = False, Eje_X = False, Angulo = 360, Reverso = 0):
	Doblez6_Base3 = Crear_Revolucion('Rev_Hole6_B001', 'Rev_Hueco6_B001', Cuerpo_B1, Boceto_Doblez6, DL6, 90, 1)
	
	Doc.recompute()
	
	# Crear_PlanoRef(Titulo, Etiqueta = '', Objeto_X = False, Eje_X = '', Modelado_X = ''):
	global DP6
	DP6 = Crear_PlanoRef('DP6_Base3_B001', 'PlanRef6_Base3_B001', Cuerpo_B1, 'Edge377',  Doblez6_Base3)
	DP6.AttachmentOffset = App.Placement(App.Vector(0, 0, -4.5), App.Rotation(0, 90, 0))
	DP6.Visibility = False
	
	# Crear_Boceto(Titulo, Etiqueta = '', Objeto_X = False, Plano_X = '', Modelado_X = '', Mapa_X = 'FlatFace'):
	Boceto_Tab6 = Crear_Boceto('Sketch_Tab6_B001', 'B_Tab6_B001', Cuerpo_B1, Modelado_X = DP6)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab6, 9, 9, 'B', math.radians(180), 2)
	
	# Actualizar_Lista(Boceto_X):
	Actualizar_Lista(Boceto_Tab6)
	Actualizar_Lista2(Boceto_Tab6)
	
	global Tab6_Base3
	# Crear_Relleno(Titulo, Etiqueta = '', Objeto_X = False, Boceto_X = False):
	Tab6_Base3 = Crear_Relleno('Pad_Tab6_B001', 'Relleno_Tab6_B001', Cuerpo_B1, Boceto_Tab6)
	Tab6_Base3.setExpression('Length', u'' + Variable_B1.Name + '.Espesor')
	
	Doc.recompute()
	
	
	
def Crear_Doblez07():
	
	### iniciar la orden PartDesign_Sketch
	global Boceto_Doblez7
	# Crear_Boceto(Titulo, Etiqueta = '', Objeto_X = False, Plano_X = '', Modelado_X = '', Mapa_X = 'FlatFace'):
	Boceto_Doblez7 = Crear_Boceto('Sketch_Fold7_B001', 'B_Doblez7_B001', Cuerpo_B1, 'Face112', Tab6_Base3, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez7, 'Esquina', Var_E, 9)
	
	Doc.recompute()
	
	# Actualizar_Lista(Boceto_X):
	Actualizar_Lista(Boceto_Doblez7)
	Actualizar_Lista2(Boceto_Doblez7)
	
	global Doblez7_Base3
	# Crear_Revolucion(Titulo, Etiqueta = '', Objeto_X = False, Boceto_X = False, Eje_X = False, Angulo = 360, Reverso = 0):
	Doblez7_Base3 = Crear_Revolucion('Rev_Hole7_B001', 'Rev_Hueco7_B001', Cuerpo_B1, Boceto_Doblez7, DL7, 90, 1)
	
	Doc.recompute()
	
	# Crear_PlanoRef(Titulo, Etiqueta = '', Objeto_X = False, Eje_X = '', Modelado_X = ''):
	global DP7
	DP7 = Crear_PlanoRef('DP7_Base3_B001', 'PlanRef7_Base3_B001', Cuerpo_B1, 'Edge397',  Doblez7_Base3)
	DP7.AttachmentOffset = App.Placement(App.Vector(0, 0, -4.5), App.Rotation(0, 90, 0))
	DP7.Visibility = False
	
	# Crear_Boceto(Titulo, Etiqueta = '', Objeto_X = False, Plano_X = '', Modelado_X = '', Mapa_X = 'FlatFace'):
	Boceto_Tab7 = Crear_Boceto('Sketch_Tab7_B001', 'B_Tab7_B001', Cuerpo_B1, Modelado_X = DP7)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab7, 9, 9, 'B', math.radians(180), 2)
	
	# Actualizar_Lista(Boceto_X):
	Actualizar_Lista(Boceto_Tab7)
	Actualizar_Lista2(Boceto_Tab7)
	
	global Tab7_Base3
	# Crear_Relleno(Titulo, Etiqueta = '', Objeto_X = False, Boceto_X = False):
	Tab7_Base3 = Crear_Relleno('Pad_Tab7_B001', 'Relleno_Tab7_B001', Cuerpo_B1, Boceto_Tab7)
	Tab7_Base3.setExpression('Length', u'' + Variable_B1.Name + '.Espesor')
	
	Doc.recompute()
	
	
	
def Crear_Doblez08():
	
	### iniciar la orden PartDesign_Sketch
	global Boceto_Doblez8
	# Crear_Boceto(Titulo, Etiqueta = '', Objeto_X = False, Plano_X = '', Modelado_X = '', Mapa_X = 'FlatFace'):
	Boceto_Doblez8 = Crear_Boceto('Sketch_Fold8_B001', 'B_Doblez8_B001', Cuerpo_B1, 'Face123', Tab7_Base3, 'InertialCS')
	
	Var_E = App.Units.Quantity(Variable_B1.Espesor).Value
	# Crear_Cuadrado(Pt1, Boceto_X, Tipo = 'Borde', Dist_X = False, Dist_Y = False, Radio = False, Angulo = 0, Guia = False, Grupo = '-'):
	Crear_Cuadrado(App.Vector(0, 0, 0), Boceto_Doblez8, 'Esquina', Var_E, 9)
	
	Doc.recompute()
	
	# Actualizar_Lista(Boceto_X):
	Actualizar_Lista(Boceto_Doblez8)
	Actualizar_Lista2(Boceto_Doblez8)
	
	global Doblez8_Base3
	# Crear_Revolucion(Titulo, Etiqueta = '', Objeto_X = False, Boceto_X = False, Eje_X = False, Angulo = 360, Reverso = 0):
	Doblez8_Base3 = Crear_Revolucion('Rev_Hole8_B001', 'Rev_Hueco8_B001', Cuerpo_B1, Boceto_Doblez8, DL8, 90, 1)
	
	Doc.recompute()
	
	# Crear_PlanoRef(Titulo, Etiqueta = '', Objeto_X = False, Eje_X = '', Modelado_X = ''):
	global DP8
	DP8 = Crear_PlanoRef('DP8_Base3_B001', 'PlanRef8_Base3_B001', Cuerpo_B1, 'Edge415',  Doblez8_Base3)
	DP8.AttachmentOffset = App.Placement(App.Vector(0, 0, -4.5), App.Rotation(0, 90, 0))
	DP8.Visibility = False
	
	# Crear_Boceto(Titulo, Etiqueta = '', Objeto_X = False, Plano_X = '', Modelado_X = '', Mapa_X = 'FlatFace'):
	Boceto_Tab8 = Crear_Boceto('Sketch_Tab8_B001', 'B_Tab8_B001', Cuerpo_B1, Modelado_X = DP8)
	
	# Crear_Semicirculo(Pt1, Boceto_X, Dist_X = False, Dist_Y = False, Tipo = 'B', Angulo = 0, Radio_Centro = False, Guia = False, Grupo = '-'):
	Crear_Semicirculo(App.Vector(0, -9 / 2, 0), Boceto_Tab8, 9, 9, 'B', math.radians(180), 2)
	
	# Actualizar_Lista(Boceto_X):
	Actualizar_Lista(Boceto_Tab8)
	Actualizar_Lista2(Boceto_Tab8)
	
	global Tab8_Base3
	# Crear_Relleno(Titulo, Etiqueta = '', Objeto_X = False, Boceto_X = False):
	Tab8_Base3 = Crear_Relleno('Pad_Tab8_B001', 'Relleno_Tab8_B001', Cuerpo_B1, Boceto_Tab8)
	Tab8_Base3.setExpression('Length', u'' + Variable_B1.Name + '.Espesor')
	
	Doc.recompute()
	
	
	
def Crear_Huecos04_3D(LaT, AnT, AlT):
	
	### iniciar la orden PartDesign_Sketch
	global Boceto_Hueco4
	# Crear_Boceto(Titulo, Etiqueta = '', Objeto_X = False, Plano_X = '', Modelado_X = '', Mapa_X = 'FlatFace'):
	Boceto_Hueco4 = Crear_Boceto('Sketch_HuecoBase4_B001', 'B_HuecoBase4_B001', Cuerpo_B1, 'Face52', Tab8_Base3, 'InertialCS')
	
	Var_E = App.Units.Quantity(Variable_B1.Espesor).Value
	Var_R = 6.35 * (1 - math.cos(math.radians(45)))
	Var_L = ((AlT - 2 * Var_R) / math.cos(math.radians(45)) + 2 * 6.35 * math.cos(math.radians(45))) / 2
	
	# Crear_Ranura(Pt1, Boceto_X, Dist_X = False, Dist_Y = False, Angulo = 0, Guia = False, Grupo = '-'):
	Crear_Ranura(App.Vector(Var_L - 9.5 / 2 - 8, 0, 0), Boceto_Hueco4, 51.9, 9.5, math.radians(90), Grupo = 'R1')
	Boceto_Hueco4.setExpression('Constraints[32]', u'' + Variable_B1.Name + '.Ancho - 38.1 mm')
	Boceto_Hueco4.renameConstraint(32, u'' + Pieza_B1.Name + '_H4-R1_H')
	#Boceto_Hueco4.setExpression('Constraints[41]', u'((' + Variable_B1.Name + '.Alto - 2 * 6.35 * (1 - math.cos(math.radians(45)))) / math.cos(math.radians(45))) / 2 - ' + str(9.5 / 2 + 5) + ' mm')
	#Boceto_Hueco4.renameConstraint(41, u'' + Pieza_B1.Name + '_H4-R1_X')
	
	
	# Crear_Cuadrado(Pt1, Boceto_X, Tipo = 'Borde', Dist_X = False, Dist_Y = False, Radio = False, Angulo = 0, Guia = False, Grupo = '-'):
	Crear_Cuadrado(App.Vector(Var_L - 8 / 2, 0, 0), Boceto_Hueco4, 'Esquina', 32.85, 8, Angulo = math.radians(90), Grupo = 'C2')
	Boceto_Hueco4.setExpression('Constraints[50]', u'' + Variable_B1.Name + '.Ancho - 57.15 mm')
	Boceto_Hueco4.renameConstraint(50, u'' + Pieza_B1.Name + '_H4-C2_H')
	#Boceto_Hueco4.setExpression('Constraints[60]', u'((' + Variable_B1.Name + '.Alto - 2 * 6.35 * (1 - math.cos(math.radians(45)))) / math.cos(math.radians(45))) / 2 - ' + str(5 / 2) + ' mm')
	#Boceto_Hueco4.renameConstraint(60, u'' + Pieza_B1.Name + '_H4-C2_X')
	Boceto_Hueco4.AttachmentOffset = App.Placement(App.Vector(0, 0, 0), App.Rotation(App.Vector(0, 0, 1), 180))
	
	
	Doc.recompute()
	
	# Actualizar_Lista(Boceto_X):
	Actualizar_Lista(Boceto_Hueco4)
	Actualizar_Lista2(Boceto_Hueco4)
	
	global Hueco_Base4
	# Crear_Hueco(Titulo, Etiqueta = '', Objeto_X = False, Boceto_X = False):
	Hueco_Base4 = Crear_Hueco('Pocket_Base4_B001', 'Hueco_Base4_B001', Cuerpo_B1, Boceto_Hueco4)
	Hueco_Base4.SideType = 2
	Hueco_Base4.Type = 1
	
	Doc.recompute()
	
	
	
def Crear_Huecos05_3D(LaT, AnT, AlT):
	
	### iniciar la orden PartDesign_Sketch
	global Boceto_Hueco5
	# Crear_Boceto(Titulo, Etiqueta = '', Objeto_X = False, Plano_X = '', Modelado_X = '', Mapa_X = 'FlatFace'):
	Boceto_Hueco5 = Crear_Boceto('Sketch_HuecoBase5_B001', 'B_HuecoBase5_B001', Cuerpo_B1, 'Face48', Hueco_Base4, 'InertialCS')
	
	Var_E = App.Units.Quantity(Variable_B1.Espesor).Value
	Var_R = 6.35 * (1 - math.cos(math.radians(45)))
	Var_L = ((AlT - 2 * Var_R) / math.cos(math.radians(45)) + 2 * 6.35 * math.cos(math.radians(45))) / 2
	
	# Crear_Ranura(Pt1, Boceto_X, Dist_X = False, Dist_Y = False, Angulo = 0, Guia = False, Grupo = '-'):
	Crear_Ranura(App.Vector(Var_L - 9.5 / 2 - 8, 0, 0), Boceto_Hueco5, 51.9, 9.5, math.radians(90), Grupo = 'R1')
	Boceto_Hueco5.setExpression('Constraints[32]', u'' + Variable_B1.Name + '.Ancho - 38.1 mm')
	Boceto_Hueco5.renameConstraint(32, u'' + Pieza_B1.Name + '_H5-R1_H')
	#Boceto_Hueco5.setExpression('Constraints[41]', u'((' + Variable_B1.Name + '.Alto - 2 * 6.35 * (1 - math.cos(math.radians(45)))) / math.cos(math.radians(45))) / 2 - ' + str(9.5 / 2 + 5) + ' mm')
	#Boceto_Hueco5.renameConstraint(41, u'' + Pieza_B1.Name + '_H5-R1_X')
	
	
	# Crear_Cuadrado(Pt1, Boceto_X, Tipo = 'Borde', Dist_X = False, Dist_Y = False, Radio = False, Angulo = 0, Guia = False, Grupo = '-'):
	Crear_Cuadrado(App.Vector(Var_L - 8 / 2, 0, 0), Boceto_Hueco5, 'Esquina', 32.85, 8, Angulo = math.radians(90), Grupo = 'C2')
	Boceto_Hueco5.setExpression('Constraints[50]', u'' + Variable_B1.Name + '.Ancho - 57.15 mm')
	Boceto_Hueco5.renameConstraint(50, u'' + Pieza_B1.Name + '_H5-C2_H')
	#Boceto_Hueco5.setExpression('Constraints[60]', u'((' + Variable_B1.Name + '.Alto - 2 * 6.35 * (1 - math.cos(math.radians(45)))) / math.cos(math.radians(45))) / 2 - ' + str(5 / 2) + ' mm')
	#Boceto_Hueco5.renameConstraint(60, u'' + Pieza_B1.Name + '_H5-C2_X')
	Boceto_Hueco5.MapReversed = True
	
	
	Doc.recompute()
	
	# Actualizar_Lista(Boceto_X):
	Actualizar_Lista(Boceto_Hueco5)
	Actualizar_Lista2(Boceto_Hueco5)
	
	global Hueco_Base5
	# Crear_Hueco(Titulo, Etiqueta = '', Objeto_X = False, Boceto_X = False):
	Hueco_Base5 = Crear_Hueco('Pocket_Base5_B001', 'Hueco_Base5_B001', Cuerpo_B1, Boceto_Hueco5)
	Hueco_Base5.SideType = 2
	Hueco_Base5.Type = 1
	
	Doc.recompute()
	
	
	
def Crear_Relleno01_3D(LaT, AnT, AlT):
	
	### iniciar la orden PartDesign_Sketch
	global Boceto_Relleno1
	# Crear_Boceto(Titulo, Etiqueta = '', Objeto_X = False, Plano_X = '', Modelado_X = '', Mapa_X = 'FlatFace'):
	Boceto_Relleno1 = Crear_Boceto('Sketch_RellenoBase6_B001', 'B_RellenoBase6_B001', Cuerpo_B1, 'Face52', Tab8_Base3, 'InertialCS')
	
	Var_E = App.Units.Quantity(Variable_B1.Espesor).Value
	Var_R = 6.35 * (1 - math.cos(math.radians(45)))
	Var_L = ((AlT - 2 * Var_R) / math.cos(math.radians(45)) + 2 * 6.35 * math.cos(math.radians(45))) / 2
	
	# Crear_Cuadrado(Pt1, Boceto_X, Tipo = 'Borde', Dist_X = False, Dist_Y = False, Radio = False, Angulo = 0, Guia = False, Grupo = '-'):
	Crear_Cuadrado(App.Vector(Var_L - 8 / 2, 0, 0), Boceto_Relleno1, 'Esquina', 32.85, 8, Angulo = math.radians(90), Grupo = 'C1')
	Crear_Cuadrado(App.Vector(Var_L - 8 / 2, 0, 0), Boceto_Relleno1, 'Esquina', 32.85 - 2 * Var_E, 8 - 2 * Var_E, Angulo = math.radians(90), Grupo = 'C2')
	#Boceto_Hueco5.setExpression('Constraints[50]', u'' + Variable_B1.Name + '.Ancho - 57.15 mm')
	#Boceto_Hueco5.renameConstraint(50, u'' + Pieza_B1.Name + '_H6-C1_H')
	#Boceto_Hueco5.setExpression('Constraints[60]', u'((' + Variable_B1.Name + '.Alto - 2 * 6.35 * (1 - math.cos(math.radians(45)))) / math.cos(math.radians(45))) / 2 - ' + str(5 / 2) + ' mm')
	#Boceto_Hueco5.renameConstraint(60, u'' + Pieza_B1.Name + '_H6-C1_X')
	Boceto_Relleno1.AttachmentOffset = App.Placement(App.Vector(0, 0, -3),  App.Rotation(0, 0, 0))
	Boceto_Relleno1.MapReversed = True
	
	Doc.recompute()
	
	# Actualizar_Lista(Boceto_X):
	Actualizar_Lista(Boceto_Relleno1)
	Actualizar_Lista2(Boceto_Relleno1)
	
	global Relleno_Base6
	# Crear_Relleno(Titulo, Etiqueta = '', Objeto_X = False, Boceto_X = False):
	Relleno_Base6 = Crear_Relleno('Pad_Base6_B001', 'Relleno_Base6_B001', Cuerpo_B1, Boceto_Relleno1)
	Relleno_Base6.Length = 25.4
	
	Doc.recompute()
	
	
	
def Crear_Relleno02_3D(LaT, AnT, AlT):
	
	### iniciar la orden PartDesign_Sketch
	global Boceto_Relleno2
	# Crear_Boceto(Titulo, Etiqueta = '', Objeto_X = False, Plano_X = '', Modelado_X = '', Mapa_X = 'FlatFace'):
	Boceto_Relleno2 = Crear_Boceto('Sketch_RellenoBase7_B001', 'B_RellenoBase7_B001', Cuerpo_B1, 'Face48', Hueco_Base4, 'InertialCS')
	
	Var_E = App.Units.Quantity(Variable_B1.Espesor).Value
	Var_R = 6.35 * (1 - math.cos(math.radians(45)))
	Var_L = ((AlT - 2 * Var_R) / math.cos(math.radians(45)) + 2 * 6.35 * math.cos(math.radians(45))) / 2
	
	# Crear_Cuadrado(Pt1, Boceto_X, Tipo = 'Borde', Dist_X = False, Dist_Y = False, Radio = False, Angulo = 0, Guia = False, Grupo = '-'):
	Crear_Cuadrado(App.Vector(-Var_L + 8 / 2, 0, 0), Boceto_Relleno2, 'Esquina', 32.85, 8, Angulo = math.radians(90), Grupo = 'C3')
	Crear_Cuadrado(App.Vector(-Var_L + 8 / 2, 0, 0), Boceto_Relleno2, 'Esquina', 32.85 - 2 * Var_E, 8 - 2 * Var_E, Angulo = math.radians(90), Grupo = 'C4')
	#Boceto_Hueco5.setExpression('Constraints[50]', u'' + Variable_B1.Name + '.Ancho - 57.15 mm')
	#Boceto_Hueco5.renameConstraint(50, u'' + Pieza_B1.Name + '_H6-C1_H')
	#Boceto_Hueco5.setExpression('Constraints[60]', u'((' + Variable_B1.Name + '.Alto - 2 * 6.35 * (1 - math.cos(math.radians(45)))) / math.cos(math.radians(45))) / 2 - ' + str(5 / 2) + ' mm')
	#Boceto_Hueco5.renameConstraint(60, u'' + Pieza_B1.Name + '_H6-C1_X')
	Boceto_Relleno2.AttachmentOffset = App.Placement(App.Vector(0, 0, -3),  App.Rotation(0, 0, 0))
	#Boceto_Relleno2.MapReversed = True
	
	Doc.recompute()
	
	# Actualizar_Lista(Boceto_X):
	Actualizar_Lista(Boceto_Relleno2)
	Actualizar_Lista2(Boceto_Relleno2)
	
	global Relleno_Base7
	# Crear_Relleno(Titulo, Etiqueta = '', Objeto_X = False, Boceto_X = False):
	Relleno_Base7 = Crear_Relleno('Pad_Base7_B001', 'Relleno_Base7_B001', Cuerpo_B1, Boceto_Relleno2)
	Relleno_Base7.Length = 25.4
	
	Doc.recompute()
	
	
	
	
	
	
	
	
	
	
	
	
	
	
	
	
	
	
	
	


#! Variable Global
#$ Esta es la memoria de los Objetos 2D para revision y analisis
# Lista_Obj = [
#	ID objeto, Longitud / Radio, Lista punto inicial, Lista punto final, Lista centro / NA,
#   Nombre del Objeto, Nombre del Contenedor
# ]
Lista_Obj = []
Lista_Res = []

dias = ('Lun', 'Mar', 'Mie', 'Jue', 'Vie', 'Sab', 'Dom')
Ini = time.time()

#! Esta es la funcion que inicia la Macro
# Crear_Hoop2(Largo_Total, Ancho_Total, Alto_Total):
Crear_Hoop2('495 mm', '90 mm', '19 mm')


# Imprimir_Lista(Lista_X, Nom_Lista = 'Lista X'):
Imprimir_Lista(Lista_Obj, 'Lista_Objetos')
Imprimir_Lista2(Lista_Res, 'Lista_Restriccion')

Fin = time.time()
indice = datetime.date.weekday(datetime.datetime.now())

print()

App.Console.PrintMessage(f'Fin de la {Pieza_B1.Label} en {round(Fin - Ini, 2)} seg\n')

print(f'{dias[indice]}  {time.strftime("%d/%m/%Y  %H:%M:%S", time.localtime())}')
