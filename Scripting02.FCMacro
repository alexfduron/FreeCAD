#Diseño parametrico de una Caja


'''
##############################################################################
#'                                                                          '#
#'                                                                          '#
#'   Copyright (c) 2026                                                     '#
#'   Original code by:                                                      '#
#'                       :::====   :::=====  :::====                        '#
#'                       :::  ===  :::       :::  ===                       '#
#'                       ========  ======    ===  ===                       '#
#'                       ===  ===  ===       ===  ===                       '#
#'                       ===  ===  ===       =======                        '#
#'                                                                          '#
#'   This program is free software, you can redistribute it and/or modify   '#
#'   it under the terms of the GNU Lesser General Public Licence ( LGPL )   '#
#'   as published by the Free Software Fundation;  either  version  2  of   '#
#'   the Licence, or (at your option) any later version.                    '#
#'   for detail see the LICENCE text file.                                  '#
#'                                                                          '#
#'   Use at your own risk. The author assumes no liability for data loss.   '#
#'              It is advised to backup your data frequently.               '#
#'             If you do not trust the software do not use it.              '#
#'                                                                          '#
#'   This software is distributed in the hope that  it  will  be  useful,   '#
#'   but WITHOUT ANY WARRANTY,  without  even  the  implied  warranty  of   '#
#'   MERCHANTABILITY  or  FITNESS  FOR  A  PARTICULAR  PURPOSE.  See  the   '#
#'   GNU Library General Public Licence for more details.                   '#
#'                                                                          '#
#'   You should have received a copy of the GNU  Library  General  Public   '#
#'   Licence along with this macro,  if not, write to the  Free  Software   '#
#'   Foundation Inc., 59 Temple Place, Suite 330,  Boston,  MA 02111-1307   '#
#'   USA.                                                                   '#
#'                                                                          '#
#'                                                                          '#
##############################################################################
'''

__Title__    = "FC_Test"
__Author__   = "AFD"
__Version__  = "1.1.0rc3"
__Date__     = "2026/03/09" #YYYY/MMM/DD

__Comment__  = "Esta macro crea una caja siguiendo las instrucciones de Juan Garcia"
__Web__      = "https://youtu.be/eH_ov9cd_Tc?is=6O9Sgimp2lbeZCkn"
__Help__     = "inicia la Macro y sigue las instrucciones"
__Status__   = "estable"
__Requires__ = "freecad 1.1.0rc3 and higher"


# importamos la libreria de "FreeCAD"
import FreeCAD as App
# importamo las librerias de "FreeCADGui" y "PySide" para limpiar la consola de python y la vista de informe
import FreeCADGui as Gui
from PySide import QtGui
# importamos la libreria de "PartDesign"
import PartDesign
# importamos la libreria de "Sketcher"
import Sketcher

# importamos la libreria de "math" para las funciones trigonometricas
import math
# importamos la libreria de "pandas" para el manejo de listas y tablas
import pandas as pd
# importamos la libreria de "datetime" para los nombres de la semana
import datetime
# importamos la libreria "time" para obtener la hora del sistema
import time



def Imprimir_Lista(Lista_X, Nom_Lista = 'Lista X'):
	
	# Aqui ajustamos las opciones de Pandas
	pd.set_option('display.max_columns', None)
	pd.set_option('display.max_rows', None)
	pd.set_option('display.width', 150)
	df = pd.DataFrame(Lista_X)
	
	# Aqui modificamos la apariencia de los datos
	df[1] = df[1].apply(lambda x : str(round(x, 3)).rstrip('0').rstrip('.'))
	df[2] = df[2].apply(lambda x : [ str(float(round(n, 3))).rstrip('0').rstrip('.').center(3) for n in x ])
	df[3] = df[3].apply(lambda x : [ str(float(round(n, 3))).rstrip('0').rstrip('.').center(3) for n in x ])
	df[4] = df[4].apply(lambda x : [ str(float(round(n, 3))).rstrip('0').rstrip('.').center(3) for n in x ])
	
	# Aqui agregamos los encabezados de las columnas
	newRow = pd.DataFrame(["ID objeto", "Longitud", "Punto inicio", "Punto final", "Centro curva", "Nombre objeto", "Contenedor"]).T
	df = df.set_axis(newRow.values[0], axis = "columns")
	df = pd.concat([df[:0], newRow.rename(columns=dict(zip(newRow.columns, df.columns))), df[0:]]).reset_index(drop = True)
	
	df = df.add_prefix("--", axis = "index")
	df = df.add_suffix("--", axis = "index")
	
	# Aqui mostramos la tabla en la consola de FreeCAD
	print(f'{Nom_Lista} = {len(Lista_X)}')
	print(df)
	
	print()
	
	
	
def Limpiar_Pantalla():
	
	mw = Gui.getMainWindow()
	
	rv = mw.findChild(QtGui.QTextEdit, "Report view")
	rv.clear()
	
	pc = mw.findChild(QtGui.QPlainTextEdit,"Python console")
	pc.onClearConsole()
	
	

#! Estas son las funciones para las partes que forman la caja
def Crear_Caja(Largo_Total, Ancho_Total, Alto_Total):
	
	# aqui convertimos el texto a numero con las unidades por defecto en FreeCAD
	try:
		LaT = App.Units.Quantity(Largo_Total).Value
	except:
		raise TypeError(f'\n\n\t Mensaje = No es Numero \n\t Funcion = Crear_Caja \n\t (Largo_Total) = "{Largo_Total}"  ==>  {type(Largo_Total)}')
	
	try:
		AnT = App.Units.Quantity(Ancho_Total).Value
	except:
		raise TypeError(f'\n\n\t Mensaje = No es Numero \n\t Funcion = Crear_Caja \n\t (Ancho_Total) = "{Ancho_Total}"  ==>  {type(Ancho_Total)}')
	try:
		AlT = App.Units.Quantity(Alto_Total).Value
	except:
		raise TypeError(f'\n\n\t Mensaje = No es Numero \n\t Funcion = Crear_Caja \n\t (Alto_Total) = "{Alto_Total}"  ==>  {type(Alto_Total)}')
	
	# Limpiar_Pantalla():
	Limpiar_Pantalla()
	
	# Crear_Contenedor_3D(LaT, AnT, AlT):
	Crear_Contenedor_3D(LaT, AnT, AlT)
	
	# Crear_Caja_3D():
	Crear_Caja_3D()
	
	# Crear_Hueco_3D():
	Crear_Hueco_3D()
	
	# Crear_Columna_3D():
	Crear_Columna_3D()
	
	# Crear_Agujero_3D():
	Crear_Agujero_3D()
	
	
	
#! Crea el contenedor del objeto 3D
def Crear_Contenedor_3D(LaT, AnT, AlT):
	
	### iniciar la orden Std_Part
	global Pieza_C1
	Pieza_C1 = Crear_Pieza('Part_C001', 'Pieza_C001')
	
	global Variable_C1
	### iniciar la orden Var_Set
	Variable_C1 = Crear_Variables('VarSet001', 'Variables001', Pieza_C1, LaT, AnT, AlT)
	
	### iniciar la orden PartDesign_Body
	global Cuerpo_C1
	Cuerpo_C1 = Crear_Cuerpo('Body_C001', 'Cuerpo_C001', Pieza_C1)
	
	
	
def Crear_Pieza(Titulo, Etiqueta = ''):
	
	Crear_Doc()
	Pieza_X = Doc.addObject('App::Part', Titulo)
	Doc.Tip = Pieza_X
	Pieza_X.Label = Etiqueta
	Doc.recompute()
	return Pieza_X
	


def Crear_Doc():
	
	# Tomamos el archivo activo
	global Doc
	Doc = App.activeDocument()
	
	

def Crear_Variables(Titulo, Etiqueta, Objeto_X, LaT, AnT, AlT):
	
	# creamos las variables del objeto
	Var_X = Doc.addObject("App::VarSet", Titulo)
	Var_X.Label = Etiqueta
	Objeto_X.addObject(Var_X)
	
	
	Var_X.addProperty("App::PropertyLength", "Largo",     group="Grupo_Caja",    doc="Esta propiedad modifica el Largo de la caja")
	Var_X.Largo = LaT
	Var_X.addProperty("App::PropertyLength", "Ancho",     group="Grupo_Caja",    doc="Esta propiedad modifica el Ancho de la caja")
	Var_X.Ancho = AnT
	Var_X.addProperty("App::PropertyLength", "Alto",      group="Grupo_Caja",    doc="Esta propiedad modifica el Alto de la caja")
	Var_X.Alto = AlT
	Var_X.addProperty("App::PropertyLength", "Espesor",   group="Grupo_Caja",    doc="Esta propiedad modifica el grosor de pared de la caja")
	Var_X.Espesor = "5 mm"
	
	Var_X.addProperty("App::PropertyLength", "Diametro_1",		group="Grupo_Opcional", 		doc="Esta propiedad modifica el diametro del cilindro")
	Var_X.Diametro_1 = "7 mm"
	Var_X.addProperty("App::PropertyLength", "Distancia_X",		group="Grupo_Opcional",		doc="Esta propiedad modifica la posicion del accesorio en x")
	Var_X.Distancia_X = "10 mm"
	Var_X.addProperty("App::PropertyLength", "Distancia_Y",		group="Grupo_Opcional",		doc="Esta propiedad modifica la posicion del accesorio en y")
	Var_X.Distancia_Y = "15 mm"
	Var_X.addProperty("App::PropertyLength", "Altura_1",			group="Grupo_Opcional",		doc="Esta propiedad modifica la altura del cilindro")
	Var_X.Altura_1 = "20 mm"
	
	Doc.recompute()
	return Var_X
	
	
	
def Crear_Cuerpo(Titulo, Etiqueta = '', Objeto_X = False):
	
	Cuerpo_X = Doc.addObject('PartDesign::Body', Titulo)
	if Etiqueta == '':
		Cuerpo_X.Label = Titulo
	else:
		Cuerpo_X.Label = Etiqueta
	if Objeto_X == False:
		Doc.Tip = Cuerpo_X
	else:
		Objeto_X.addObject(Cuerpo_X)
	Doc.recompute()
	return Cuerpo_X
	
	
	
def Crear_Boceto(Titulo, Etiqueta = '', Objeto_X = False, Plano_X = '', Modelado_X = ''):
	
	Boceto_X = Doc.addObject('Sketcher::SketchObject', Titulo)
	Doc.Tip = Boceto_X
	if Etiqueta == '':
		Boceto_X.Label = Titulo
	else:
		Boceto_X.Label = Etiqueta
	Boceto_X.MapMode = 'FlatFace'
	if Modelado_X == '':
		Plano_X = 'XY_Plane'
		if Objeto_X == False:
			if Plano_X == '':
				Plano_X = 'XY_Plane'
			Doc.Tip = Boceto_X
			Cuerpo_New = Crear_Cuerpo('New_Body', '', Pieza_C1)
			Cuerpo_New.addObject(Boceto_X)
			for k in Cuerpo_New.Origin.OriginFeatures:
				if k.Role == Plano_X:
					XY_Plano = k
			Boceto_X.AttachmentSupport = (Cuerpo_New.Origin, [XY_Plano.Name])
			del XY_Plano
		else:
			if Plano_X == '':
				Plano_X = 'XY_Plane'
			Objeto_X.addObject(Boceto_X)
			for k in Objeto_X.Origin.OriginFeatures:
				if k.Role == Plano_X:
					XY_Plano = k
			Boceto_X.AttachmentSupport = (Objeto_X.Origin, [XY_Plano.Name])
			del XY_Plano
	else:
		Objeto_X.addObject(Boceto_X)
		Boceto_X.AttachmentSupport = (Modelado_X, [Plano_X])
		
	Doc.recompute()
	return Boceto_X	
	

	
#! Estos son las funciones para crear Objetos 2D
def Crear_Linea(Pt1, Pt2, Boceto_X, Guia = False):
	
	# aqui guardamos el ID de la linea.
	Lista_Obj.append(list(Boceto_X.addGeometry([Part.LineSegment(Pt1, Pt2)], Guia)))
	# aqui redondeamos los valores numericos de los vectores
	Pt1_Temp = [round(Pt1[0], 10), round(Pt1[1], 10), round(Pt1[2], 10)]
	Pt2_Temp = [round(Pt2[0], 10), round(Pt2[1], 10), round(Pt2[2], 10)]
	# aqui guardamos la magnitud de la linea.
	Pt3 = App.Vector(Pt2) - App.Vector(Pt1)
	Lista_Obj[-1].append(round(Pt3.Length, 10))
	# aqui guardamos el punto inicial de la linea.
	Lista_Obj[-1].append(Pt1_Temp)
	# aqui guardamos el punto final de la linea.
	Lista_Obj[-1].append(Pt2_Temp)
	# aqui guardamos el punto centro => N/A.
	Lista_Obj[-1].append([0.0, 0.0, 0.0])
	# aqui guardamos el nombre de la linea.
	Lista_Obj[-1].append('linea')
	# aqui guardamos el Boceto que contiene la linea.
	Lista_Obj[-1].append(Boceto_X.Label)
	


def Crear_Arco(Pt1, Eje, Radio, Boceto_X, Ang_Ini, Ang_Fin, Guia = False):
	
	# aqui guardamos el ID del arco.
	Lista_Obj.append(list(Boceto_X.addGeometry([Part.ArcOfCircle(Part.Circle(Pt1, Eje , Radio), Ang_Ini, Ang_Fin)], Guia)))
	# aqui creamos los puntos de los extremos del arco con los valores numericos redondeados
	Pt1_Temp = App.Vector(round(Pt1.x + Radio * math.cos(Ang_Ini), 10), round(Pt1.y + Radio * math.sin(Ang_Ini), 10), round(Pt1.z, 10))
	Pt2_Temp = App.Vector(round(Pt1.x + Radio * math.cos(Ang_Fin), 10), round(Pt1.y + Radio * math.sin(Ang_Fin), 10), round(Pt1.z, 10))
	Eje_Temp = App.Vector(round(Pt1.x, 10), round(Pt1.y, 10), round(Pt1.z, 10))
	# aqui guardamos el radio del arco.
	Lista_Obj[-1].append(round(Radio, 10))
	# aqui guardamos el punto inicial del arco.
	Lista_Obj[-1].append(list(Pt1_Temp))
	# aqui guardamos el punto final del arco.
	Lista_Obj[-1].append(list(Pt2_Temp))
	# aqui guardamos el punto central del arco.
	Lista_Obj[-1].append(list(Eje_Temp))
	# aqui guardamos el nombre del arco.
	Lista_Obj[-1].append('arco')
	# aqui guardamos el Boceto que contiene al arco.
	Lista_Obj[-1].append(Boceto_X.Label)
	


def Crear_Circulo(Pt1, Eje, Radio, Boceto_X, Guia = False):
	
	# aqui guardamos el ID del circulo.
	Lista_Obj.append(list(Boceto_X.addGeometry([Part.Circle(Pt1, Eje, Radio)], Guia)))
	# aqui creamos el punto centro del circulo con los valores numericos redondeados
	Eje_Temp = App.Vector(round(Pt1.x, 10), round(Pt1.y, 10), round(Pt1.z, 10))
	# aqui guardamos el radio del circulo.
	Lista_Obj[-1].append(round(Radio, 10))
	# aqui guardamos el punto inicial del circulo => N/A.
	Lista_Obj[-1].append([0, 0, 0])
	# aqui guardamos el punto final del circulo => N/A.
	Lista_Obj[-1].append([0, 0, 0])
	# aqui guardamos el punto central del circulo.
	Lista_Obj[-1].append(list(Eje_Temp))
	# aqui guardamos el nombre del circulo.
	Lista_Obj[-1].append('circulo')
	# aqui guardamos el Boceto que contiene al circulo.
	Lista_Obj[-1].append(Boceto_X.Label)
	
	
	
#! Estos son las funciones para crear Modelado 3D
def Crear_Relleno(Titulo, Etiqueta = '', Objeto_X = False, Boceto_X = False):
	
	Relleno_X = Doc.addObject('PartDesign::Pad', Titulo)
	if Objeto_X == False:
		Doc.Tip = Relleno_X
	else:
		Objeto_X.addObject(Relleno_X)
	if Etiqueta == '':
		Relleno_X.Label = Titulo
	else:
		Relleno_X.Label = Etiqueta
	
	Relleno_X.Profile = (Boceto_X, [''])
	Relleno_X.ReferenceAxis = (Boceto_X,['N_Axis'])
	Boceto_X.Visibility = False
	
	Doc.recompute()
	return Relleno_X
	
	
	
def Crear_Hueco(Titulo, Etiqueta = '', Objeto_X = False, Boceto_X = False):
	
	Hueco_X = Doc.addObject('PartDesign::Pocket', Titulo)
	if Objeto_X == False:
		Doc.Tip = Hueco_X
	else:
		Objeto_X.addObject(Hueco_X)
	if Etiqueta == '':
		Hueco_X.Label = Titulo
	else:
		Hueco_X.Label = Etiqueta
	
	Hueco_X.Profile = (Boceto_X, [''])
	Hueco_X.ReferenceAxis = (Boceto_X,['N_Axis'])
	Boceto_X.Visibility = False
	
	Doc.recompute()
	return Hueco_X
	
	
	
def Crear_Agujero(Titulo, Etiqueta = '', Objeto_X = False, Boceto_X = False, Plano_X = '', Modelado_X = ''):
	
	Agujero_X = Doc.addObject('PartDesign::Hole', Titulo)
	if Objeto_X == False:
		Doc.Tip = Agujero_X
	else:
		Objeto_X.addObject(Agujero_X)
	if Etiqueta == '':
		Agujero_X.Label = Titulo
	else:
		Agujero_X.Label = Etiqueta
	
	if Boceto_X == False:
		Agujero_X.Profile = (Modelado_X, [Plano_X])
	else:
		Agujero_X.Profile = (Boceto_X, [''])
		Boceto_X.Visibility = False
	
	Doc.recompute()
	return Agujero_X
	
	
	
#! crear Caja 3D
def Crear_Caja_3D():
	
	### iniciar la orden PartDesign_Sketch
	global Boceto_Base
	# Crear_Boceto(Titulo, Etiqueta = '', Objeto_X = False, Plano_X = '', Modelado_X = ''):
	Boceto_Base = Crear_Boceto('Sketch_Base_C001', 'Boceto_Base_C001', Cuerpo_C1)
	
	# creamos la lista de puntos por cada linea
	geoList = []
	# [Punto inicial, Punto final]
	geoList.append([App.Vector(20, 90, 0),  App.Vector(20, 20, 0)])
	geoList.append([App.Vector(20, 20, 0),  App.Vector(100, 20, 0)])
	geoList.append([App.Vector(100, 20, 0), App.Vector(100, 90, 0)])
	geoList.append([App.Vector(100, 90, 0), App.Vector(20, 90, 0)])
	
	for NewLinea in geoList:
		# Crear_Linea(Pt1, Pt2, Boceto_X, Guia = False):
		Crear_Linea(NewLinea[0], NewLinea[1], Boceto_Base)
	
	del geoList
	
	# creamos la lista de restricciones
	constraintList = []
	constraintList.append(Sketcher.Constraint('Coincident', 0, 2, 1, 1))		#Constraints[0]
	constraintList.append(Sketcher.Constraint('Coincident', 1, 2, 2, 1))		#Constraints[1]
	constraintList.append(Sketcher.Constraint('Coincident', 2, 2, 3, 1))		#Constraints[2]
	constraintList.append(Sketcher.Constraint('Coincident', 3, 2, 0, 1))		#Constraints[3]
	constraintList.append(Sketcher.Constraint('Vertical', 0))				#Constraints[4]
	constraintList.append(Sketcher.Constraint('Vertical', 2))				#Constraints[5]
	constraintList.append(Sketcher.Constraint('Horizontal', 1))				#Constraints[6]
	constraintList.append(Sketcher.Constraint('Horizontal', 3))				#Constraints[7]
	constraintList.append(Sketcher.Constraint('DistanceX',3,2,3,1,80))		#Constraints[8]
	constraintList.append(Sketcher.Constraint('DistanceY',2,1,2,2,70))		#Constraints[9]
	constraintList.append(Sketcher.Constraint('Coincident',0,2,-1,1))		#Constraints[10]
	
	Boceto_Base.addConstraint(constraintList)
	
	Boceto_Base.setExpression('Constraints[8]', u'' + Variable_C1.Name + '.Ancho')
	Boceto_Base.setExpression('Constraints[9]', u'' + Variable_C1.Name + '.Largo')
	
	del constraintList
	
	Doc.recompute()
	
	global Relleno_Base
	# Crear_Relleno(Titulo, Etiqueta = '', Objeto_X = False, Boceto_X = False):
	Relleno_Base = Crear_Relleno('Pad_Base_C001', 'Relleno_Base_C001', Cuerpo_C1, Boceto_Base)
	Relleno_Base.setExpression('Length', u'' + Variable_C1.Name + '.Alto + ' + Variable_C1.Name + '.Espesor')
	
	Doc.recompute()
	
	
	
def Crear_Hueco_3D():
	
	### iniciar la orden PartDesign_Sketch
	global Boceto_Hueco
	# Crear_Boceto(Titulo, Etiqueta = '', Objeto_X = False, Plano_X = '', Modelado_X = ''):
	Boceto_Hueco = Crear_Boceto('Sketch_Hueco_C001', 'Boceto_Hueco_C001', Cuerpo_C1, 'Face6', Relleno_Base)
	
	# creamos la lista de puntos por cada linea
	geoList = []
	# [Punto inicial, Punto final]
	geoList.append([App.Vector(20, 90, 0),  App.Vector(20, 20, 0)])
	geoList.append([App.Vector(20, 20, 0),  App.Vector(100, 20, 0)])
	geoList.append([App.Vector(100, 20, 0), App.Vector(100, 90, 0)])
	geoList.append([App.Vector(100, 90, 0), App.Vector(20, 90, 0)])
	
	for NewLinea in geoList:
		# Crear_Linea(Pt1, Pt2, Boceto_X, Guia = False):
		Crear_Linea(NewLinea[0], NewLinea[1], Boceto_Hueco)
	
	del geoList
	
	# Creamos la lista de restricciones
	constraintList = []
	constraintList.append(Sketcher.Constraint('Coincident', 0, 2, 1, 1))		#Constraints[0]
	constraintList.append(Sketcher.Constraint('Coincident', 1, 2, 2, 1))		#Constraints[1]
	constraintList.append(Sketcher.Constraint('Coincident', 2, 2, 3, 1))		#Constraints[2]
	constraintList.append(Sketcher.Constraint('Coincident', 3, 2, 0, 1))		#Constraints[3]
	constraintList.append(Sketcher.Constraint('Vertical', 0))				#Constraints[4]
	constraintList.append(Sketcher.Constraint('Vertical', 2))				#Constraints[5]
	constraintList.append(Sketcher.Constraint('Horizontal', 1))				#Constraints[6]
	constraintList.append(Sketcher.Constraint('Horizontal', 3))				#Constraints[7]
	constraintList.append(Sketcher.Constraint('DistanceX',3,2,3,1,20))		#Constraints[8]
	constraintList.append(Sketcher.Constraint('DistanceY',2,1,2,2,40))		#Constraints[9]
	constraintList.append(Sketcher.Constraint('DistanceX',-1,1,0,2,5))		#Constraints[10]
	constraintList.append(Sketcher.Constraint('DistanceY',-1,1,0,2,5))		#Constraints[11]
	
	Boceto_Hueco.addConstraint(constraintList)
	
	Boceto_Hueco.setExpression('Constraints[8]', u'' + Variable_C1.Name + '.Ancho - 2 * ' + Variable_C1.Name + '.Espesor')
	Boceto_Hueco.setExpression('Constraints[9]', u'' + Variable_C1.Name + '.Largo - 2 * ' + Variable_C1.Name + '.Espesor')
	Boceto_Hueco.setExpression('Constraints[10]', u'' + Variable_C1.Name + '.Espesor')
	Boceto_Hueco.setExpression('Constraints[11]', u'' + Variable_C1.Name + '.Espesor')
	
	del constraintList
	
	Doc.recompute()
	
	global Hueco_Base
	# Crear_Hueco(Titulo, Etiqueta = '', Objeto_X = False, Boceto_X = False):
	Hueco_Base = Crear_Hueco('Pocket_Base_C001', 'Hueco_Base_C001', Cuerpo_C1, Boceto_Hueco)
	Hueco_Base.setExpression('Length', u'' + Variable_C1.Name + '.Alto')
	Relleno_Base.Visibility = False
	
	Doc.recompute()
	
	
	
def Crear_Columna_3D():
	
	### iniciar la orden PartDesign_Sketch
	global Boceto_Columna
	# Crear_Boceto(Titulo, Etiqueta = '', Objeto_X = False, Plano_X = '', Modelado_X = ''):
	Boceto_Columna = Crear_Boceto('Sketch_Columna_C001', 'Boceto_Columna_C001', Cuerpo_C1, 'Face11', Hueco_Base)
	
	# creamos la lista de puntos por cada circulo
	geoList = []
	# [Punto centro, Vector normal, Radio]
	geoList.append([App.Vector(10, 50, 0), App.Vector(0, 0, 1), 5])
	geoList.append([App.Vector(20, 50, 0), App.Vector(0, 0, 1), 5])
	geoList.append([App.Vector(10, 10, 0), App.Vector(0, 0, 1), 5])
	geoList.append([App.Vector(20, 10, 0), App.Vector(0, 0, 1), 5])
	
	for NewCirculo in geoList:
		# Crear_Circulo(Pt1, Eje, Radio, Boceto_X, Guia = False):
		Crear_Circulo(NewCirculo[0], NewCirculo[1], NewCirculo[2], Boceto_Columna)
	
	del geoList
	
	# Creamos la lista de restricciones
	constraintList = []
	constraintList.append(Sketcher.Constraint('Horizontal',0,3,1,3))		#Constraints[0]
	constraintList.append(Sketcher.Constraint('Vertical',0,3,2,3))		#Constraints[1]
	constraintList.append(Sketcher.Constraint('Vertical',1,3,3,3))		#Constraints[2]
	constraintList.append(Sketcher.Constraint('Horizontal',2,3,3,3))		#Constraints[3]
	constraintList.append(Sketcher.Constraint('Diameter',0,5))			#Constraints[4]
	constraintList.append(Sketcher.Constraint('Diameter',1,5))			#Constraints[5]
	constraintList.append(Sketcher.Constraint('Diameter',2,5))			#Constraints[6]
	constraintList.append(Sketcher.Constraint('Diameter',3,5))			#Constraints[7]
	constraintList.append(Sketcher.Constraint('DistanceY',2,3,0,3,30))	#Constraints[8]
	constraintList.append(Sketcher.Constraint('DistanceX',2,3,3,3,20))	#Constraints[9]
	constraintList.append(Sketcher.Constraint('DistanceY',-1,1,2,3,10))	#Constraints[10]
	constraintList.append(Sketcher.Constraint('DistanceX',-1,1,2,3,10))	#Constraints[11]
	
	Boceto_Columna.addConstraint(constraintList)
	
	Boceto_Columna.setExpression('Constraints[4]', u'' + Variable_C1.Name + '.Diametro_1')
	Boceto_Columna.setExpression('Constraints[5]', u'' + Variable_C1.Name + '.Diametro_1')
	Boceto_Columna.setExpression('Constraints[6]', u'' + Variable_C1.Name + '.Diametro_1')
	Boceto_Columna.setExpression('Constraints[7]', u'' + Variable_C1.Name + '.Diametro_1')
	Boceto_Columna.setExpression('Constraints[8]', u'' + Variable_C1.Name + '.Largo - 2 * ' + Variable_C1.Name + '.Distancia_Y')
	Boceto_Columna.setExpression('Constraints[9]', u'' + Variable_C1.Name + '.Ancho - 2 * ' + Variable_C1.Name + '.Distancia_X')
	Boceto_Columna.setExpression('Constraints[10]', u'' + Variable_C1.Name + '.Distancia_Y')
	Boceto_Columna.setExpression('Constraints[11]', u'' + Variable_C1.Name + '.Distancia_X')
	
	del constraintList
	
	Doc.recompute()
	
	global Relleno_Columna
	# Crear_Relleno(Titulo, Etiqueta = '', Objeto_X = False, Boceto_X = False):
	Relleno_Columna = Crear_Relleno('Pad_Columna_C001', 'Relleno_Columna_C001', Cuerpo_C1, Boceto_Columna)
	Relleno_Columna.setExpression('Length', u'' + Variable_C1.Name + '.Altura_1')
	Hueco_Base.Visibility = False
	
	Doc.recompute()
	
	
	
def Crear_Agujero_3D():
	
	### iniciar la orden PartDesign_Sketch
	global Boceto_Agujero
	# Crear_Boceto(Titulo, Etiqueta = '', Objeto_X = False, Plano_X = '', Modelado_X = ''):
	Boceto_Agujero = Crear_Boceto('Sketch_Agujero_C001', 'Boceto_Agujero_C001', Cuerpo_C1, 'Face18', Relleno_Columna)
	
	# creamos la lista de puntos por cada circulo
	geoList = []
	# [Punto centro, Vector normal, Radio]
	geoList.append([App.Vector(10, 50, 0), App.Vector(0, 0, 1), 5])
	geoList.append([App.Vector(20, 50, 0), App.Vector(0, 0, 1), 5])
	geoList.append([App.Vector(10, 10, 0), App.Vector(0, 0, 1), 5])
	geoList.append([App.Vector(20, 10, 0), App.Vector(0, 0, 1), 5])
	
	for NewCirculo in geoList:
		# Crear_Circulo(Pt1, Eje, Radio, Boceto_X, Guia = False):
		Crear_Circulo(NewCirculo[0], NewCirculo[1], NewCirculo[2], Boceto_Agujero)
	
	del geoList
	
	# Creamos la lista de restricciones
	constraintList = []
	constraintList.append(Sketcher.Constraint('Horizontal',0,3,1,3))		#Constraints[0]
	constraintList.append(Sketcher.Constraint('Vertical',0,3,2,3))		#Constraints[1]
	constraintList.append(Sketcher.Constraint('Vertical',1,3,3,3))		#Constraints[2]
	constraintList.append(Sketcher.Constraint('Horizontal',2,3,3,3))		#Constraints[3]
	constraintList.append(Sketcher.Constraint('Diameter',0,5))			#Constraints[4]
	constraintList.append(Sketcher.Constraint('Diameter',1,5))			#Constraints[5]
	constraintList.append(Sketcher.Constraint('Diameter',2,5))			#Constraints[6]
	constraintList.append(Sketcher.Constraint('Diameter',3,5))			#Constraints[7]
	constraintList.append(Sketcher.Constraint('DistanceY',2,3,0,3,30))	#Constraints[8]
	constraintList.append(Sketcher.Constraint('DistanceX',2,3,3,3,20))	#Constraints[9]
	constraintList.append(Sketcher.Constraint('DistanceY',-1,1,2,3,10))	#Constraints[10]
	constraintList.append(Sketcher.Constraint('DistanceX',-1,1,2,3,10))	#Constraints[11]
	
	Boceto_Agujero.addConstraint(constraintList)
	
	Boceto_Agujero.setExpression('Constraints[4]', u'' + Variable_C1.Name + '.Diametro_1')
	Boceto_Agujero.setExpression('Constraints[5]', u'' + Variable_C1.Name + '.Diametro_1')
	Boceto_Agujero.setExpression('Constraints[6]', u'' + Variable_C1.Name + '.Diametro_1')
	Boceto_Agujero.setExpression('Constraints[7]', u'' + Variable_C1.Name + '.Diametro_1')
	Boceto_Agujero.setExpression('Constraints[8]', u'' + Variable_C1.Name + '.Largo - 2 * ' + Variable_C1.Name + '.Distancia_Y')
	Boceto_Agujero.setExpression('Constraints[9]', u'' + Variable_C1.Name + '.Ancho - 2 * ' + Variable_C1.Name + '.Distancia_X')
	Boceto_Agujero.setExpression('Constraints[10]', u'' + Variable_C1.Name + '.Distancia_Y')
	Boceto_Agujero.setExpression('Constraints[11]', u'' + Variable_C1.Name + '.Distancia_X')
	
	del constraintList
	
	Doc.recompute()
	
	global Agujero_Base
	# Crear_Agujero(Titulo, Etiqueta = '', Objeto_X = False, Boceto_X = False, Plano_X = '', Modelado_X = ''):
	Agujero_Base = Crear_Agujero('Hole_C001', 'Agujero_C001', Cuerpo_C1, Boceto_Agujero)
	Agujero_Base.setExpression('Depth', u'' + Variable_C1.Name + '.Altura_1')
	Agujero_Base.ThreadType = 1
	Agujero_Base.ThreadSize = 9
	#Agujero_Base.Threaded = 1
	#Agujero_Base.ModelThread = 1
	Relleno_Columna.Visibility = False
	
	
	
	


#! Variable Global
#$ Esta es la memoria de los Objetos 2D para revision y analisis
# Lista_Obj = [
#	ID objeto, Longitud / Radio, Lista punto inicial, Lista punto final, Lista centro / NA,
#   Nombre del Objeto, Nombre del Contenedor
# ]
Lista_Obj = []

dias = ('Lun', 'Mar', 'Mie', 'Jue', 'Vie', 'Sab', 'Dom')
Ini = time.time()

#! Esta es la funcion que inicia la Macro
# Crear_Caja(Largo_Total, Ancho_Total, Alto_Total):
Crear_Caja('60 mm', '40 mm', '20 mm')


# Imprimir_Lista(Lista_X, Nom_Lista = 'Lista X'):
Imprimir_Lista(Lista_Obj, 'Lista_Objetos')

Fin = time.time()
indice = datetime.date.weekday(datetime.datetime.now())

print()

App.Console.PrintMessage(f'Fin de la {Pieza_C1.Label} en {round(Fin - Ini, 2)} seg\n')

print(f'{dias[indice]}  {time.strftime("%d/%m/%Y  %H:%M:%S", time.localtime())}')
