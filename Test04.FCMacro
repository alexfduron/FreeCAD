import FreeCAD as App
from PySide import QtGui
import PartDesignGui
import PartDesign
import Sketcher
import Part
import math
import datetime
import time






def Limpiar_Pantalla():
	
	mw = Gui.getMainWindow()
	rv = mw.findChild(QtGui.QTextEdit, "Report view")
	rv.clear()
	
	pc = mw.findChild(QtGui.QPlainTextEdit,"Python console")



def Crear_Pieza(Titulo, Etiqueta = ''):
	
	# creamos el contenedor principal
	Pieza_X = Doc.addObject('App::Part', Titulo)
	Pieza_X.Label = Etiqueta
	Doc.recompute()
	
	return Pieza_X
	
	
	
def Crear_Grupo(Titulo, Etiqueta = '', Pieza_X = False):
	
	Grupo_X = Doc.addObject('App::DocumentObjectGroup', Titulo)
	Doc.Tip = Grupo_X
	if Etiqueta == '':
		Grupo_X.Label = Titulo
	else:
		Grupo_X.Label = Etiqueta
	if Pieza_X == False:
		Doc.Tip = Grupo_X
	else:
		Pieza_X.addObject(Grupo_X)
	Doc.recompute()
	
	return Grupo_X
	
	
	
def Crear_Variable(Titulo, Etiqueta = '', Objeto_X = False):
	
	# creamos las variables del objeto
	Var_X = Doc.addObject("App::VarSet", Titulo)
	Var_X.Label = Etiqueta
	Objeto_X.addObject(Var_X)
	Var_X.addProperty("App::PropertyLength", "Aro_Largo", group="Grupo_2D_Aro", doc="Esta propiedad modifica el Largo del Aro")
	Var_X.Aro_Largo = "156 mm"
	Var_X.addProperty("App::PropertyLength", "Aro_Alto", group="Grupo_2D_Aro", doc="Esta propiedad modifica el Alto del Aro")
	Var_X.Aro_Alto = "156 mm"
	Var_X.addProperty("App::PropertyLength", "Aro_Radio", group="Grupo_2D_Aro", doc="Esta propiedad modifica el Radio interior del Aro")
	Var_X.Aro_Radio = "35 mm"
	Var_X.addProperty("App::PropertyLength", "Radio_Agujero", group="Grupo_2D_Radio", doc="Esta propiedad modifica el Radio del Agujero")
	Var_X.Radio_Agujero = "1.5 mm"
	Var_X.addProperty("App::PropertyLength", "Radio_Iman", group="Grupo_2D_Radio", doc="Esta propiedad modifica el Radio del Iman")
	Var_X.Radio_Iman = "7 mm"
	Var_X.addProperty("App::PropertyLength", "Aro_Grosor", group="Grupo_2D_Grosor", doc="Esta propiedad modifica el Grosor del Aro")
	Var_X.Aro_Grosor = "14 mm"
	Var_X.addProperty("App::PropertyLength", "Aro_Margen", group="Grupo_2D_Grosor", doc="Esta propiedad modifica el Margen del Aro")
	Var_X.Aro_Margen = "1 mm"
	Doc.recompute()
	
	return Var_X
	
	
	
def Crear_Cuerpo(Titulo, Etiqueta = '', Pieza_X = False):
	
	# creamos el contenedor cuerpo
	Cuerpo_X = Doc.addObject('PartDesign::Body', Titulo)
	Cuerpo_X.Label = Etiqueta
	Pieza_X.addObject(Cuerpo_X)
	Doc.recompute()
	
	return Cuerpo_X
	
	
	
def Crear_Boceto(Titulo, Etiqueta = '', Cuerpo_X = False):
	
	# creamos el contenedor boceto
	Boceto_X = Doc.addObject('Sketcher::SketchObject', Titulo)
	Boceto_X.Label = Etiqueta
	Boceto_X.MapMode = 'FlatFace'
	Cuerpo_X.addObject(Boceto_X)
	for k in Cuerpo_X.Origin.OriginFeatures:
		if k.Role == 'XY_Plane':
			XY_Plano = k
	Boceto_X.AttachmentSupport = (XY_Plano, [''])
	del XY_Plano
	Doc.recompute()
	
	return Boceto_X
	
	
	
def Crear_Relleno(Cuerpo_X, Boceto_X, Altura_X):
	
	# creamos el contenedor 3D relleno
	Relleno_X = Doc.addObject('PartDesign::Pad', 'Pad001')
	Relleno_X.Label = 'Relleno001'
	Cuerpo_X.addObject(Relleno_X)
	Relleno_X.Profile = (Boceto_X, ['',])
	#Relleno_X.Length = App.Units.Quantity('40 mm')
	Relleno_X.Length = Altura_X
	Relleno_X.ReferenceAxis = (Boceto_X,['N_Axis'])
	Relleno_X.Midplane = 1
	Boceto_X.Visibility = False
	Doc.recompute()
	
	return Relleno_X
	
	
	
def Crear_Hueco(Cuerpo_X, Boceto_X, Altura_X):
	
	# creamos el contenedor 3D Hueco
	Hueco_X = Doc.addObject('PartDesign::Pocket', 'Pocket001')
	Hueco_X.Label = 'Hueco001'
	Cuerpo_X.addObject(Hueco_X)
	Hueco_X.Profile = (Boceto_X, ['',])
	#Hueco_X.Length = App.Units.Quantity('40 mm')
	Hueco_X.Length = Altura_X
	Hueco_X.ReferenceAxis = (Boceto_X,['N_Axis'])
	Hueco_X.Midplane = 1
	Boceto_X.Visibility = False
	Doc.recompute()
	
	return Hueco_X
	
	
	
def Crear_Filete(Cuerpo_X, Radio_X, Forma_X, Lista_X):
	
	# creamos el contenedor 3D Filete
	Filete_X = Doc.addObject('PartDesign::Fillet', 'Fillet001')
	Filete_X.Label = 'Filete001'
	Cuerpo_X.addObject(Filete_X)
	Filete_X.Base = (Forma_X, Lista_X)
	#Filete_X.Radio = App.Units.Quantity('40 mm')
	Filete_X.Radius = Radio_X
	Forma_X.Visibility = False
	Doc.recompute()
	
	return Filete_X
	
	
	
def Crear_Chaflan(Cuerpo_X, Medida_X, Forma_X, Lista_X):
	
	# creamos el contenedor 3D Chaflan
	Chaflan_X = Doc.addObject('PartDesign::Chamfer', 'Chamfer001')
	Chaflan_X.Label = 'Chaflan001'
	Cuerpo_X.addObject(Chaflan_X)
	Chaflan_X.Base = (Forma_X, Lista_X)
	#Chaflan_X.Radio = App.Units.Quantity('40 mm')
	Chaflan_X.Size = Medida_X
	Forma_X.Visibility = False
	Doc.recompute()
	
	return Chaflan_X
	
	
	
def Imprimir_Lista(Indice = -1):
	if Indice == -1:
		pass
	else:
		print(f'{Indice = }')
	
	print(f'{len(Lista_Obj) = }')
	for l in Lista_Obj:
		print(l)
	
	print()
	print(f'{len(Lista_Restr) = }')
	for l in Lista_Restr:
		print(l)
	
	
	
def Crear_Contenedor():
	
	global Doc
	Doc = App.activeDocument()
	
	global Lista_Obj
	Lista_Obj = []
	
	global Lista_Restr
	Lista_Restr = []
	
	
	
	global Pieza01
	# Crear_Pieza(Titulo, Etiqueta = ''):
	Pieza01 = Crear_Pieza('Par_001', 'Pieza_001')
	
	global Variable01
	# Crear_Variable(Titulo, Etiqueta = '', Objeto_X = False):
	Variable01 = Crear_Variable('Var_001', 'Variables', Pieza01)
	
	global Grupo_2D
	# Crear_Grupo(Titulo, Etiqueta = '', Pieza_X = False):
	Grupo_2D = Crear_Grupo('Gro_001', 'Grupo_2D', Pieza01)
	
	global Cuerpo_2D
	# Crear_Cuerpo(Titulo, Etiqueta = '', Pieza_X = False):
	Cuerpo_2D = Crear_Cuerpo('Bod_001', 'Cuerpo_2D', Grupo_2D)
	
	global Boceto_G2D_B
	# Crear_Boceto(Titulo, Etiqueta = '', Cuerpo_X):
	Boceto_G2D_B = Crear_Boceto('Ske_001', 'Boceto_Base', Cuerpo_2D)
	
	global Boceto_G2D_T
	# Crear_Boceto(Titulo, Etiqueta = '', Cuerpo_X):
	Boceto_2D_T = Crear_Boceto('Ske_002', 'Boceto_Tapadera', Cuerpo_2D)
	
	
	
	
	
	
def Crear_Linea(Obj_X, Dir_X, Pt1, Pt2, Boceto_X, Grupo_X = 'G_01', Visible = False):
	
	# aqui guardamos el ID de la linea.
	Lista_Obj.append(list(Boceto_X.addGeometry([Part.LineSegment(Pt1, Pt2)], Visible)))
	# aqui redondeamos los valores numericos de los vectores
	Pt1_Temp = App.Vector(round(Pt1.x, 10), round(Pt1.y, 10), round(Pt1.z, 10))
	Pt2_Temp = App.Vector(round(Pt2.x, 10), round(Pt2.y, 10), round(Pt2.z, 10))
	# aqui guardamos el punto inicial: Pt1 => (1) y punto final: Pt2 => (2) de la linea.
	Lista_Obj[-1].append(1)
	Lista_Obj[-1].append(2)
	# aqui guardamos el nombre de la linea.
	Lista_Obj[-1].append(Obj_X)
	# aqui guardamos la direccion de la linea
	Lista_Obj[-1].append(Dir_X)
	# aqui guardamos el nombre del contenedor.
	Lista_Obj[-1].append(Boceto_X.Name)
	# aqui guardamos la magnitud de la linea.
	Pt3 = Pt2 - Pt1
	Lista_Obj[-1].append(round(Pt3.Length, 10))
	# aqui guardamos el punto inicial de la linea.
	Lista_Obj[-1].append(list(Pt1_Temp))
	# aqui guardamos el punto final de la linea.
	Lista_Obj[-1].append(list(Pt2_Temp))
	# aqui guardamos el punto centro => N/A.
	Lista_Obj[-1].append([0.0, 0.0, 0.0])
	# aqui guardamos el nombre del sub-grupo.
	Lista_Obj[-1].append(Grupo_X)
	
	
	
def Crear_Arco(Obj_X, Dir_X, Pt1, Eje, Radio, Ang_Ini, Ang_Fin, Boceto_X, Grupo_X = 'G_01', Visible = False):
	
	# aqui guardamos el ID del arco.
	Lista_Obj.append(list(Boceto_X.addGeometry([Part.ArcOfCircle(Part.Circle(Pt1, Eje , Radio), Ang_Ini, Ang_Fin)], Visible)))
	# aqui creamos los puntos de los extremos del arco con los valores numericos redondeados (Ang_Ini => Pt1 Temp, Ang_Fin => Pt2_Temp)
	Pt1_Temp = App.Vector(round(Pt1.x + Radio * math.cos(Ang_Ini), 10), round(Pt1.y + Radio * math.sin(Ang_Ini), 10), round(Pt1.z, 10))
	Pt2_Temp = App.Vector(round(Pt1.x + Radio * math.cos(Ang_Fin), 10), round(Pt1.y + Radio * math.sin(Ang_Fin), 10), round(Pt1.z, 10))
	Eje_Temp = App.Vector(round(Pt1.x, 10), round(Pt1.y, 10), round(Pt1.z, 10))
	# aqui guardamos el punto inicial: Pt1_Temp => (1) y punto final: Pt2_Temp => (2) del arco.
	Lista_Obj[-1].append(1)
	Lista_Obj[-1].append(2)
	# aqui guardamos el nombre del arco.
	Lista_Obj[-1].append(Obj_X)
	# aqui guardamos la direccion del arco
	Lista_Obj[-1].append(Dir_X)
	# aqui guardamos el Boceto que contiene al arco.
	Lista_Obj[-1].append(Boceto_X.Name)
	# aqui guardamos el radio del arco.
	Lista_Obj[-1].append(round(Radio, 10))
	# aqui guardamos el punto inicial del arco.
	Lista_Obj[-1].append(list(Pt1_Temp))
	# aqui guardamos el punto final del arco.
	Lista_Obj[-1].append(list(Pt2_Temp))
	# aqui guardamos el punto central del arco.
	Lista_Obj[-1].append(list(Eje_Temp))
	# aqui guardamos el nombre del sub-grupo.
	Lista_Obj[-1].append(Grupo_X)
	
	
	
def Crear_Circulo(Obj_X, Dir_X, Pt1, Eje, Radio, Boceto_X, Grupo_X = 'G_01', Visible = False):
	
	# aqui guardamos el ID del circulo.
	Lista_Obj.append(list(Boceto_X.addGeometry([Part.Circle(Pt1, Eje, Radio)], Visible)))
	# aqui creamos los puntos del centro circulo con los valores numericos redondeados
	Eje_Temp = App.Vector(round(Pt1.x, 10), round(Pt1.y, 10), round(Pt1.z, 10))
	# aqui guardamos el punto inicial => (1) y punto final => (2) del circulo => N/A.
	Lista_Obj[-1].append(0)
	Lista_Obj[-1].append(0)
	# aqui guardamos el nombre del circulo.
	Lista_Obj[-1].append(Obj_X)
	# aqui guardamos la direccion del circulo
	Lista_Obj[-1].append(Dir_X)
	# aqui guardamos el Boceto que contiene al circulo.
	Lista_Obj[-1].append(Boceto_X.Name)
	# aqui guardamos el radio del circulo.
	Lista_Obj[-1].append(round(Radio, 10))
	# aqui guardamos el punto inicial del circulo => N/A.
	Lista_Obj[-1].append(0)
	# aqui guardamos el punto final del circulo => N/A.
	Lista_Obj[-1].append(0)
	# aqui guardamos el punto central del circulo.
	Lista_Obj[-1].append(list(Eje_Temp))
	# aqui guardamos el nombre del sub-grupo.
	Lista_Obj[-1].append(Grupo_X)
	
	
	
def Validar_Puntos_de_Contacto(Total_Lista):
	
	for j in range(0, Total_Lista)[::-1]:
		Valor_Futuro = (j - 1) % Total_Lista
		
		# aqui validamos que los puntos sean coincidentes
		
		if Lista_Obj[::-1][j][7] == Lista_Obj[::-1][Valor_Futuro][6]:
			
			if Lista_Obj[::-1][j][2] == 2:
				pass
			else:
				Temp = Lista_Obj[::-1][j][1]
				Lista_Obj[::-1][j][1] = Lista_Obj[::-1][j][2]
				Lista_Obj[::-1][j][2] = Temp
				
			if Lista_Obj[::-1][Valor_Futuro][1] == 1:
				pass
			else:
				Temp = Lista_Obj[::-1][Valor_Futuro][2]
				Lista_Obj[::-1][Valor_Futuro][2] = Lista_Obj[::-1][Valor_Futuro][1]
				Lista_Obj[::-1][Valor_Futuro][1] = Temp
				
		elif Lista_Obj[::-1][j][7] == Lista_Obj[::-1][Valor_Futuro][7]:
			
			if Lista_Obj[::-1][j][2] == 2:
				pass
			else:
				Temp = Lista_Obj[::-1][j][1]
				Lista_Obj[::-1][j][1] = Lista_Obj[::-1][j][2]
				Lista_Obj[::-1][j][2] = Temp
				
			if Lista_Obj[::-1][Valor_Futuro][1] == 2:
				pass
			else:
				Temp = Lista_Obj[::-1][Valor_Futuro][2]
				Lista_Obj[::-1][Valor_Futuro][2] = Lista_Obj[::-1][Valor_Futuro][1]
				Lista_Obj[::-1][Valor_Futuro][1] = Temp
			
		elif Lista_Obj[::-1][j][6] == Lista_Obj[::-1][Valor_Futuro][6]:
			
			if Lista_Obj[::-1][j][2] == 1:
				pass
			else:
				Temp = Lista_Obj[::-1][j][1]
				Lista_Obj[::-1][j][1] = Lista_Obj[::-1][j][2]
				Lista_Obj[::-1][j][2] = Temp
				
			if Lista_Obj[::-1][Valor_Futuro][1] == 1:
				pass
			else:
				Temp = Lista_Obj[::-1][Valor_Futuro][2]
				Lista_Obj[::-1][Valor_Futuro][2] = Lista_Obj[::-1][Valor_Futuro][1]
				Lista_Obj[::-1][Valor_Futuro][1] = Temp
				
		elif Lista_Obj[::-1][j][6] == Lista_Obj[::-1][Valor_Futuro][7]:
			
			if Lista_Obj[::-1][j][2] == 1:
				pass
			else:
				Temp = Lista_Obj[::-1][j][1]
				Lista_Obj[::-1][j][1] = Lista_Obj[::-1][j][2]
				Lista_Obj[::-1][j][2] = Temp
				
			if Lista_Obj[::-1][Valor_Futuro][1] == 2:
				pass
			else:
				Temp = Lista_Obj[::-1][Valor_Futuro][2]
				Lista_Obj[::-1][Valor_Futuro][2] = Lista_Obj[::-1][Valor_Futuro][1]
				Lista_Obj[::-1][Valor_Futuro][1] = Temp
	
	
	
def Actualizar_Lista01(LT, AT, RT):
	
	LLX = (LT - 2 * RT) / 2
	LTX = LT / 2
	ALY = (AT - 2 * RT) / 2
	ATY = AT / 2
	RT = RT
	
	geoList = [
		['linea', 'V_L', App.Vector(-LTX, ALY, 0), App.Vector(-LTX, -ALY, 0)],
		['linea', 'H_D', App.Vector(-LLX, -ATY, 0), App.Vector(LLX, -ATY, 0)],
		['linea', 'V_R', App.Vector(LTX, -ALY, 0), App.Vector(LTX, ALY, 0)],
		['linea', 'H_U', App.Vector(LLX, ATY, 0), App.Vector(-LLX, ATY, 0)],
		
		['arco ', 'U_L', App.Vector(-LLX, ALY, 0), App.Vector(0, 0, 1), RT, math.radians(90), math.radians(180)],
		['arco ', 'D_L', App.Vector(-LLX, -ALY, 0), App.Vector(0, 0, 1), RT, math.radians(180), math.radians(270)],
		['arco ', 'D_R', App.Vector(LLX, -ALY, 0), App.Vector(0, 0, 1), RT, math.radians(270), math.radians(360)],
		['arco ', 'U_R', App.Vector(LLX, ALY, 0), App.Vector(0, 0, 1), RT, math.radians(0), math.radians(90)],
	]
	
	return geoList
	
	
	
def Actualizar_Lista02(LT, AT, RT, Dir_X):
	
	Margen = Doc.Var_001.Aro_Margen.Value
	Grosor = Doc.Var_001.Aro_Grosor.Value
	Radio  = Doc.Var_001.Radio_Agujero.Value
	Desfase = 70 / 2
	
	Var_XC = [-(LT - 2 * RT) / 2, (LT - 2 * RT) / 2]
	Var_XM = [[-LT / 2 - Margen - Grosor, -LT / 2 - Margen], [LT / 2 + Margen, LT / 2 + Margen + Grosor]]
	Var_X  = [-LT / 2 - Margen - Grosor / 2, LT / 2 + Margen + Grosor / 2]
	
	Var_YC = [(AT - 2 * RT) / 2, -(AT - 2 * RT) / 2]
	Var_YM = [[AT / 2 + Margen + Grosor, AT / 2 + Margen], [-AT / 2 - Margen, -AT / 2 - Margen - Grosor]]
	Var_Y  = [AT / 2 + Margen + Grosor / 2, -AT / 2 - Margen - Grosor / 2]
	
	if Dir_X == 'H_U':
		
		constrGeoList = [
			['linea', 'V_L', App.Vector(Var_XC[0], Var_YM[0][0], 0), App.Vector(Var_XC[0], Var_YM[0][1], 0)],
			['linea', 'V_R', App.Vector(Var_XC[1], Var_YM[0][0], 0), App.Vector(Var_XC[1], Var_YM[0][1], 0)],
			['linea', 'H_U', App.Vector(Var_XC[0], Var_Y[0],     0), App.Vector(Var_XC[1], Var_Y[0],     0)],
			['circulo', 'U__', App.Vector(-Desfase, Var_Y[0], 0), App.Vector(0, 0, 1), Radio],
			['circulo', 'U__', App.Vector( Desfase, Var_Y[0], 0), App.Vector(0, 0, 1), Radio]
		]
		
	if Dir_X == 'H_D':
		
		constrGeoList = [
			['linea', 'V_L', App.Vector(Var_XC[0], Var_YM[1][0], 0), App.Vector(Var_XC[0], Var_YM[1][1], 0)],
			['linea', 'V_R', App.Vector(Var_XC[1], Var_YM[1][0], 0), App.Vector(Var_XC[1], Var_YM[1][1], 0)],
			['linea', 'H_D', App.Vector(Var_XC[0], Var_Y[1],     0), App.Vector(Var_XC[1], Var_Y[1],     0)],
			['circulo', 'D__', App.Vector(-Desfase, Var_Y[1], 0), App.Vector(0, 0, 1), Radio],
			['circulo', 'D__', App.Vector( Desfase, Var_Y[1], 0), App.Vector(0, 0, 1), Radio]
		]
		
	if Dir_X == 'V_R':
		
		constrGeoList = [
			['linea', 'H_U', App.Vector(Var_XM[1][0], Var_YC[0], 0), App.Vector(Var_XM[1][1], Var_YC[0], 0)],
			['linea', 'H_D', App.Vector(Var_XM[1][0], Var_YC[1], 0), App.Vector(Var_XM[1][1], Var_YC[1], 0)],
			['linea', 'V_R', App.Vector(Var_X[1], Var_Y[0],      0), App.Vector(Var_X[1], Var_Y[1],      0)],
			['circulo', 'R__', App.Vector(Var_X[1],  Desfase, 0), App.Vector(0, 0, 1), Radio],
			['circulo', 'R__', App.Vector(Var_X[1], -Desfase, 0), App.Vector(0, 0, 1), Radio]
		]
		
	if Dir_X == 'V_L':
		
		constrGeoList = [
			['linea', 'H_U', App.Vector(Var_XM[0][0], Var_YC[0], 0), App.Vector(Var_XM[0][1], Var_YC[0], 0)],
			['linea', 'H_D', App.Vector(Var_XM[0][0], Var_YC[1], 0), App.Vector(Var_XM[0][1], Var_YC[1], 0)],
			['linea', 'V_L', App.Vector(Var_X[0], Var_Y[0],      0), App.Vector(Var_X[0], Var_Y[1],      0)],
			['circulo', 'L__', App.Vector(Var_X[0],  Desfase, 0), App.Vector(0, 0, 1), Radio],
			['circulo', 'L__', App.Vector(Var_X[0], -Desfase, 0), App.Vector(0, 0, 1), Radio]
		]
		
	return constrGeoList
	
	
	

	
	

	
	
	
def Crear_Boceto_Base(Largo_T, Alto_T, Radio_T):
	
	LT = App.Units.Quantity(Largo_T).Value
	AT = App.Units.Quantity(Alto_T).Value
	RT = App.Units.Quantity(Radio_T).Value
	
	# Actualizar_Lista01(LT, AT, RT):
	Lista01 = Actualizar_Lista01(LT, AT, RT)
	
	for k in range(0, len(Lista01)):
		if Lista01[k][0] == 'linea':
			# Crear_Linea(Obj_X, Dir_X, Pt1, Pt2, Boceto_X, Grupo_X = 'G_01', Visible = False):
			Crear_Linea(Lista01[k][0], Lista01[k][1], Lista01[k][2], Lista01[k][3], Boceto_G2D_B, 'G_01')
		if Lista01[k][0] == 'arco ':
			# Crear_Arco(Pt1, Eje, Radio, Ang_Ini, Ang_Fin, Boceto_X, Grupo_X = 'G_01', Visible = False):
			Crear_Arco(Lista01[k][0], Lista01[k][1], Lista01[k][2], Lista01[k][3], Lista01[k][4], Lista01[k][5], Lista01[k][6], Boceto_G2D_B, 'G_01')
	
	del Lista01
	
	constraintList = []
	constraintList.append(Sketcher.Constraint('Tangent', 0, 1, 4, 2))
	constraintList.append(Sketcher.Constraint('Tangent', 0, 2, 5, 1))
	constraintList.append(Sketcher.Constraint('Tangent', 1, 1, 5, 2))
	constraintList.append(Sketcher.Constraint('Tangent', 1, 2, 6, 1))
	constraintList.append(Sketcher.Constraint('Tangent', 2, 1, 6, 2))
	constraintList.append(Sketcher.Constraint('Tangent', 2, 2, 7, 1))
	constraintList.append(Sketcher.Constraint('Tangent', 3, 1, 7, 2))
	constraintList.append(Sketcher.Constraint('Tangent', 3, 2, 4, 1))
	constraintList.append(Sketcher.Constraint('Vertical', 0))
	constraintList.append(Sketcher.Constraint('Vertical', 2))
	constraintList.append(Sketcher.Constraint('Horizontal', 1))
	constraintList.append(Sketcher.Constraint('Horizontal', 3))
	constraintList.append(Sketcher.Constraint('Equal', 4, 5))
	constraintList.append(Sketcher.Constraint('Equal', 5, 6))
	constraintList.append(Sketcher.Constraint('Equal', 6, 7))
	constraintList.append(Sketcher.Constraint('DistanceX', 0, 1, 2, 2, 156))
	constraintList.append(Sketcher.Constraint('DistanceY', 1, 2, 3, 1, 156))
	constraintList.append(Sketcher.Constraint('Radius', 5, 35))
	constraintList.append(Sketcher.Constraint('Symmetric', 4, 3, 6, 3, -1, 1))
	
	Boceto_G2D_B.addConstraint(constraintList)
	
	del constraintList
	
	Boceto_G2D_B.renameConstraint(15, u'Largo_Total')
	Boceto_G2D_B.setVirtualSpace(15, False)
	Boceto_G2D_B.renameConstraint(16, u'Alto_Total')
	Boceto_G2D_B.setVirtualSpace(16, False)
	Boceto_G2D_B.renameConstraint(17, u'Radio_Total')
	Boceto_G2D_B.setVirtualSpace(17, False)
	Boceto_G2D_B.setExpression('.Constraints.Largo_Total', u'Var_001.Aro_Largo < 2.2 * Var_001.Aro_Radio ? 2.2 * Var_001.Aro_Radio : (Var_001.Aro_Largo > 800 ? 800 : Var_001.Aro_Largo)')
	Boceto_G2D_B.setExpression('.Constraints.Alto_Total', u'Var_001.Aro_Alto < 2.2 * Var_001.Aro_Radio ? 2.2 * Var_001.Aro_Radio : (Var_001.Aro_Alto > 800 ? 800 : Var_001.Aro_Alto)')
	Boceto_G2D_B.setExpression('.Constraints.Radio_Total', 'Var_001.Aro_Radio < 35 ? 35 : (Var_001.Aro_Radio > 50 ? 50 : Var_001.Aro_Radio)')
	
	Lista_Restr.append([15])
	Lista_Restr[-1].append('DistanceX')
	Lista_Restr[-1].append('00')
	Lista_Restr[-1].append('01')
	Lista_Restr[-1].append('02')
	Lista_Restr[-1].append('02')
	Lista_Restr[-1].append('156')
	Lista_Restr[-1].append('Largo_Total')
	Lista_Restr[-1].append('G_01')
	Lista_Restr[-1].append('NA  ')
	Lista_Restr[-1].append(Boceto_G2D_B.Name)
	
	Lista_Restr.append([16])
	Lista_Restr[-1].append('DistanceY')
	Lista_Restr[-1].append('01')
	Lista_Restr[-1].append('02')
	Lista_Restr[-1].append('03')
	Lista_Restr[-1].append('01')
	Lista_Restr[-1].append('156')
	Lista_Restr[-1].append('Alto_Total ')
	Lista_Restr[-1].append('G_01')
	Lista_Restr[-1].append('NA  ')
	Lista_Restr[-1].append(Boceto_G2D_B.Name)
	
	Lista_Restr.append([17])
	Lista_Restr[-1].append('Radius   ')
	Lista_Restr[-1].append('05')
	Lista_Restr[-1].append('NA')
	Lista_Restr[-1].append('NA')
	Lista_Restr[-1].append('NA')
	Lista_Restr[-1].append('035')
	Lista_Restr[-1].append('Radio_Total')
	Lista_Restr[-1].append('G_01')
	Lista_Restr[-1].append('NA  ')
	Lista_Restr[-1].append(Boceto_G2D_B.Name)
	
	Doc.recompute()
	
	
	
	LT += 1 + 1
	AT += 1 + 1
	RT += 1
	
	# Actualizar_Lista01(LT, AT, RT):
	Lista01 = Actualizar_Lista01(LT, AT, RT)
	
	for k in range(0, len(Lista01)):
		if Lista01[k][0] == 'linea':
			# Crear_Linea(Obj_X, Dir_X, Pt1, Pt2, Boceto_X, Grupo_X = 'G_01', Visible = False):
			Crear_Linea(Lista01[k][0], Lista01[k][1], Lista01[k][2], Lista01[k][3], Boceto_G2D_B, 'G_02')
		if Lista01[k][0] == 'arco ':
			# Crear_Arco(Obj_X, Dir_X, Pt1, Eje, Radio, Ang_Ini, Ang_Fin, Boceto_X, Grupo_X = 'G_01', Visible = False):
			Crear_Arco(Lista01[k][0], Lista01[k][1], Lista01[k][2], Lista01[k][3], Lista01[k][4], Lista01[k][5], Lista01[k][6], Boceto_G2D_B, 'G_02')
	
	del Lista01
	
	constraintList = []
	constraintList.append(Sketcher.Constraint('Tangent', 8, 1, 12, 2))
	constraintList.append(Sketcher.Constraint('Tangent', 8, 2, 13, 1))
	constraintList.append(Sketcher.Constraint('Tangent', 9, 1, 13, 2))
	constraintList.append(Sketcher.Constraint('Tangent', 9, 2, 14, 1))
	constraintList.append(Sketcher.Constraint('Tangent', 10, 1, 14, 2))
	constraintList.append(Sketcher.Constraint('Tangent', 10, 2, 15, 1))
	constraintList.append(Sketcher.Constraint('Tangent', 11, 1, 15, 2))
	constraintList.append(Sketcher.Constraint('Tangent', 11, 2, 12, 1))
	constraintList.append(Sketcher.Constraint('Vertical', 8))
	constraintList.append(Sketcher.Constraint('Vertical', 10))
	constraintList.append(Sketcher.Constraint('Horizontal', 9))
	constraintList.append(Sketcher.Constraint('Horizontal', 11))
	constraintList.append(Sketcher.Constraint('Equal', 12, 13))
	constraintList.append(Sketcher.Constraint('Equal', 13, 14))
	constraintList.append(Sketcher.Constraint('Equal', 14, 15))
	constraintList.append(Sketcher.Constraint('Coincident', 5, 3, 13, 3))
	constraintList.append(Sketcher.Constraint('Coincident', 7, 3, 15, 3))
	constraintList.append(Sketcher.Constraint('DistanceX', 2, 2, 10, 2, 1))
	
	Boceto_G2D_B.addConstraint(constraintList)
	
	del constraintList
	
	Boceto_G2D_B.renameConstraint(36, u'Margen_01')
	Boceto_G2D_B.setVirtualSpace(36, False)
	Boceto_G2D_B.setExpression('.Constraints.Margen_01', u'Var_001.Aro_Margen < 1 ? 1 : (Var_001.Aro_Margen > 10 ? 10 : Var_001.Aro_Margen)')
	
	Lista_Restr.append([36])
	Lista_Restr[-1].append('DistanceX')
	Lista_Restr[-1].append('02')
	Lista_Restr[-1].append('02')
	Lista_Restr[-1].append('10')
	Lista_Restr[-1].append('02')
	Lista_Restr[-1].append('001')
	Lista_Restr[-1].append('Margen_01  ')
	Lista_Restr[-1].append('G_01')
	Lista_Restr[-1].append('G_02')
	Lista_Restr[-1].append(Boceto_G2D_B.Name)
	
	Doc.recompute()
	
	
	
	LT += 14 + 14
	AT += 14 + 14
	RT += 14
	
	# Actualizar_Lista01(LT, AT, RT):
	Lista01 = Actualizar_Lista01(LT, AT, RT)
	
	for k in range(0, len(Lista01)):
		if Lista01[k][0] == 'linea':
			# Crear_Linea(Obj_X, Dir_X, Pt1, Pt2, Boceto_X, Grupo_X = 'G_01', Visible = False):
			Crear_Linea(Lista01[k][0], Lista01[k][1], Lista01[k][2], Lista01[k][3], Boceto_G2D_B, 'G_03')
		if Lista01[k][0] == 'arco ':
			# Crear_Arco(Obj_X, Dir_X, Pt1, Eje, Radio, Ang_Ini, Ang_Fin, Boceto_X, Grupo_X = 'G_01', Visible = False):
			Crear_Arco(Lista01[k][0], Lista01[k][1], Lista01[k][2], Lista01[k][3], Lista01[k][4], Lista01[k][5], Lista01[k][6], Boceto_G2D_B, 'G_03')
	
	del Lista01
	
	constraintList = []
	constraintList.append(Sketcher.Constraint('Tangent', 16, 1, 20, 2))
	constraintList.append(Sketcher.Constraint('Tangent', 16, 2, 21, 1))
	constraintList.append(Sketcher.Constraint('Tangent', 17, 1, 21, 2))
	constraintList.append(Sketcher.Constraint('Tangent', 17, 2, 22, 1))
	constraintList.append(Sketcher.Constraint('Tangent', 18, 1, 22, 2))
	constraintList.append(Sketcher.Constraint('Tangent', 18, 2, 23, 1))
	constraintList.append(Sketcher.Constraint('Tangent', 19, 1, 23, 2))
	constraintList.append(Sketcher.Constraint('Tangent', 19, 2, 20, 1))
	constraintList.append(Sketcher.Constraint('Vertical', 16))
	constraintList.append(Sketcher.Constraint('Vertical', 18))
	constraintList.append(Sketcher.Constraint('Horizontal', 17))
	constraintList.append(Sketcher.Constraint('Horizontal', 19))
	constraintList.append(Sketcher.Constraint('Equal', 20, 21))
	constraintList.append(Sketcher.Constraint('Equal', 21, 22))
	constraintList.append(Sketcher.Constraint('Equal', 22, 23))
	constraintList.append(Sketcher.Constraint('Coincident', 5, 3, 21, 3))
	constraintList.append(Sketcher.Constraint('Coincident', 7, 3, 23, 3))
	constraintList.append(Sketcher.Constraint('DistanceX', 10, 2, 18, 2, 14))
	
	Boceto_G2D_B.addConstraint(constraintList)
	
	del constraintList

	Boceto_G2D_B.renameConstraint(54, u'Grosor_01')
	Boceto_G2D_B.setVirtualSpace(54, False)
	Boceto_G2D_B.setExpression('.Constraints.Grosor_01', u'Var_001.Aro_Grosor < 10 ? 10 : (Var_001.Aro_Grosor > 100 ? 100 : Var_001.Aro_Grosor)')
	
	Lista_Restr.append([54])
	Lista_Restr[-1].append('DistanceX')
	Lista_Restr[-1].append('10')
	Lista_Restr[-1].append('02')
	Lista_Restr[-1].append('18')
	Lista_Restr[-1].append('02')
	Lista_Restr[-1].append('014')
	Lista_Restr[-1].append('Grosor_01  ')
	Lista_Restr[-1].append('G_02')
	Lista_Restr[-1].append('G_03')
	Lista_Restr[-1].append(Boceto_G2D_B.Name)
	
	Doc.recompute()


	
	LT += 1 + 1
	AT += 1 + 1
	RT += 1
	
	# Actualizar_Lista01(LT, AT, RT):
	Lista01 = Actualizar_Lista01(LT, AT, RT)
	
	for k in range(0, len(Lista01)):
		if Lista01[k][0] == 'linea':
			# Crear_Linea(Obj_X, Dir_X, Pt1, Pt2, Boceto_X, Grupo_X = 'G_01', Visible = False):
			Crear_Linea(Lista01[k][0], Lista01[k][1], Lista01[k][2], Lista01[k][3], Boceto_G2D_B, 'G_04')
		if Lista01[k][0] == 'arco ':
			# Crear_Arco(Obj_X, Dir_X, Pt1, Eje, Radio, Ang_Ini, Ang_Fin, Boceto_X, Grupo_X = 'G_01', Visible = False):
			Crear_Arco(Lista01[k][0], Lista01[k][1], Lista01[k][2], Lista01[k][3], Lista01[k][4], Lista01[k][5], Lista01[k][6], Boceto_G2D_B, 'G_04')
	
	del Lista01
	
	constraintList = []
	constraintList.append(Sketcher.Constraint('Tangent', 24, 1, 28, 2))
	constraintList.append(Sketcher.Constraint('Tangent', 24, 2, 29, 1))
	constraintList.append(Sketcher.Constraint('Tangent', 25, 1, 29, 2))
	constraintList.append(Sketcher.Constraint('Tangent', 25, 2, 30, 1))
	constraintList.append(Sketcher.Constraint('Tangent', 26, 1, 30, 2))
	constraintList.append(Sketcher.Constraint('Tangent', 26, 2, 31, 1))
	constraintList.append(Sketcher.Constraint('Tangent', 27, 1, 31, 2))
	constraintList.append(Sketcher.Constraint('Tangent', 27, 2, 28, 1))
	constraintList.append(Sketcher.Constraint('Vertical', 24))
	constraintList.append(Sketcher.Constraint('Vertical', 26))
	constraintList.append(Sketcher.Constraint('Horizontal', 25))
	constraintList.append(Sketcher.Constraint('Horizontal', 27))
	constraintList.append(Sketcher.Constraint('Equal', 28, 29))
	constraintList.append(Sketcher.Constraint('Equal', 29, 30))
	constraintList.append(Sketcher.Constraint('Equal', 30, 31))
	constraintList.append(Sketcher.Constraint('Coincident', 5, 3, 29, 3))
	constraintList.append(Sketcher.Constraint('Coincident', 7, 3, 31, 3))
	constraintList.append(Sketcher.Constraint('DistanceX', 18, 2, 26, 2, 1))
	
	Boceto_G2D_B.addConstraint(constraintList)
	
	del constraintList
	
	Boceto_G2D_B.renameConstraint(72, u'Margen_02')
	Boceto_G2D_B.setVirtualSpace(72, False)
	Boceto_G2D_B.setExpression('.Constraints.Margen_02', u'Var_001.Aro_Margen < 1 ? 1 : (Var_001.Aro_Margen > 10 ? 10 : Var_001.Aro_Margen)')
	
	Lista_Restr.append([72])
	Lista_Restr[-1].append('DistanceX')
	Lista_Restr[-1].append('18')
	Lista_Restr[-1].append('02')
	Lista_Restr[-1].append('26')
	Lista_Restr[-1].append('02')
	Lista_Restr[-1].append('001')
	Lista_Restr[-1].append('Margen_02  ')
	Lista_Restr[-1].append('G_03')
	Lista_Restr[-1].append('G_04')
	Lista_Restr[-1].append(Boceto_G2D_B.Name)
	
	Doc.recompute()
	
	
	
	
	
	
	
	
	
	
	
	
	LT = App.Units.Quantity(Largo_T).Value
	AT = App.Units.Quantity(Alto_T).Value
	RT = App.Units.Quantity(Radio_T).Value
	
	# Actualizar_Lista02(LT, AT, RT, Dir_X):
	Lista02 = Actualizar_Lista02(LT, AT, RT, 'H_U')
	
	for k in range(0, len(Lista02)):
		if Lista02[k][0] == 'linea':
			# Crear_Linea(Obj_X, Dir_X, Pt1, Pt2, Boceto_X, Grupo_X = 'G_01', Visible = False):
			Crear_Linea(Lista02[k][0], Lista02[k][1], Lista02[k][2], Lista02[k][3], Boceto_G2D_B, 'G_05', True)
		if Lista02[k][0] == 'circulo':
			# Crear_Circulo(Obj_X, Dir_X, Pt1, Eje, Radio, Boceto_X, Grupo_X = 'G_01', Visible = False):
			Crear_Circulo(Lista02[k][0], Lista02[k][1], Lista02[k][2], Lista02[k][3], Lista02[k][4], Boceto_G2D_B, 'G_05')
		
	del Lista02
	
	constraintList = []
	constraintList.append(Sketcher.Constraint('Coincident', 32, 1, 19, 2))
	constraintList.append(Sketcher.Constraint('Coincident', 32, 2, 11, 2))
	constraintList.append(Sketcher.Constraint('Coincident', 33, 1, 19, 1))
	constraintList.append(Sketcher.Constraint('Coincident', 33, 2, 11, 1))
	constraintList.append(Sketcher.Constraint('Symmetric', 19, 2, 11, 2, 34, 1))
	constraintList.append(Sketcher.Constraint('Symmetric', 19, 1, 11, 1, 34, 2))
	constraintList.append(Sketcher.Constraint('PointOnObject', 35, 3, 34))
	constraintList.append(Sketcher.Constraint('PointOnObject', 36, 3, 34))
	constraintList.append(Sketcher.Constraint('Equal', 35, 36))
	constraintList.append(Sketcher.Constraint('Radius', 35, 1.5))
	constraintList.append(Sketcher.Constraint('DistanceX', 35, 3, -1, 1, 35))
	constraintList.append(Sketcher.Constraint('DistanceX', -1, 1, 36, 3, 35))
	
	Boceto_G2D_B.addConstraint(constraintList)
	
	del constraintList
	
	Boceto_G2D_B.renameConstraint(82, u'Radio_01')
	Boceto_G2D_B.setVirtualSpace(82, False)
	Boceto_G2D_B.setExpression('.Constraints.Radio_01', u'Var_001.Radio_Agujero < 1 ? 1 : (Var_001.Radio_Agujero > 5 ? 5 : Var_001.Radio_Agujero)')
	
	Lista_Restr.append([82])
	Lista_Restr[-1].append('Radius   ')
	Lista_Restr[-1].append('35')
	Lista_Restr[-1].append('00')
	Lista_Restr[-1].append('00')
	Lista_Restr[-1].append('00')
	Lista_Restr[-1].append('1.5')
	Lista_Restr[-1].append('Radio_01   ')
	Lista_Restr[-1].append('G_05')
	Lista_Restr[-1].append('NA  ')
	Lista_Restr[-1].append(Boceto_G2D_B.Name)
	
	Doc.recompute()
	
	
	
	# Actualizar_Lista02(LT, AT, RT, Dir_X):
	Lista02 = Actualizar_Lista02(LT, AT, RT, 'V_R')
	
	for k in range(0, len(Lista02)):
		if Lista02[k][0] == 'linea':
			# Crear_Linea(Obj_X, Dir_X, Pt1, Pt2, Boceto_X, Grupo_X = 'G_01', Visible = False):
			Crear_Linea(Lista02[k][0], Lista02[k][1], Lista02[k][2], Lista02[k][3], Boceto_G2D_B, 'G_05', True)
		if Lista02[k][0] == 'circulo':
			# Crear_Circulo(Obj_X, Dir_X, Pt1, Eje, Radio, Boceto_X, Grupo_X = 'G_01', Visible = False):
			Crear_Circulo(Lista02[k][0], Lista02[k][1], Lista02[k][2], Lista02[k][3], Lista02[k][4], Boceto_G2D_B, 'G_05')
	
	del Lista02
	
	constraintList = []
	constraintList.append(Sketcher.Constraint('Coincident', 37, 1, 10, 2))
	constraintList.append(Sketcher.Constraint('Coincident', 37, 2, 18, 2))
	constraintList.append(Sketcher.Constraint('Coincident', 38, 1, 10, 1))
	constraintList.append(Sketcher.Constraint('Coincident', 38, 2, 18, 1))
	constraintList.append(Sketcher.Constraint('Symmetric', 10, 2, 18, 2, 39, 1))
	constraintList.append(Sketcher.Constraint('Symmetric', 10, 1, 18, 1, 39, 2))
	constraintList.append(Sketcher.Constraint('PointOnObject', 40, 3, 39))
	constraintList.append(Sketcher.Constraint('PointOnObject', 41, 3, 39))
	constraintList.append(Sketcher.Constraint('Equal', 40, 41))
	constraintList.append(Sketcher.Constraint('Radius', 40, 1.5))
	constraintList.append(Sketcher.Constraint('DistanceY', -1, 1, 40, 3, 35))
	constraintList.append(Sketcher.Constraint('DistanceY', 41, 3, -1, 1, 35))
	
	Boceto_G2D_B.addConstraint(constraintList)
	
	del constraintList
	
	Boceto_G2D_B.renameConstraint(94, u'Radio_02')
	Boceto_G2D_B.setVirtualSpace(94, False)
	Boceto_G2D_B.setExpression('.Constraints.Radio_02', u'Var_001.Radio_Agujero < 1 ? 1 : (Var_001.Radio_Agujero > 5 ? 5 : Var_001.Radio_Agujero)')
	
	Lista_Restr.append([94])
	Lista_Restr[-1].append('Radius   ')
	Lista_Restr[-1].append('40')
	Lista_Restr[-1].append('00')
	Lista_Restr[-1].append('00')
	Lista_Restr[-1].append('00')
	Lista_Restr[-1].append('1.5')
	Lista_Restr[-1].append('Radio_02   ')
	Lista_Restr[-1].append('G_05')
	Lista_Restr[-1].append('NA  ')
	Lista_Restr[-1].append(Boceto_G2D_B.Name)
	
	Doc.recompute()
	
	
	
	# Actualizar_Lista02(LT, AT, RT, Dir_X):
	Lista02 = Actualizar_Lista02(LT, AT, RT, 'H_D')
	
	for k in range(0, len(Lista02)):
		if Lista02[k][0] == 'linea':
			# Crear_Linea(Obj_X, Dir_X, Pt1, Pt2, Boceto_X, Grupo_X = 'G_01', Visible = False):
			Crear_Linea(Lista02[k][0], Lista02[k][1], Lista02[k][2], Lista02[k][3], Boceto_G2D_B, 'G_05', True)
		if Lista02[k][0] == 'circulo':
			# Crear_Circulo(Obj_X, Dir_X, Pt1, Eje, Radio, Boceto_X, Grupo_X = 'G_01', Visible = False):
			Crear_Circulo(Lista02[k][0], Lista02[k][1], Lista02[k][2], Lista02[k][3], Lista02[k][4], Boceto_G2D_B, 'G_05')
	
	del Lista02
	
	constraintList = []
	constraintList.append(Sketcher.Constraint('Coincident', 42, 1, 9, 1))
	constraintList.append(Sketcher.Constraint('Coincident', 42, 2, 17, 1))
	constraintList.append(Sketcher.Constraint('Coincident', 43, 1, 9, 2))
	constraintList.append(Sketcher.Constraint('Coincident', 43, 2, 17, 2))
	constraintList.append(Sketcher.Constraint('Symmetric', 9, 1, 17, 1, 44, 1))
	constraintList.append(Sketcher.Constraint('Symmetric', 9, 2, 17, 2, 44, 2))
	constraintList.append(Sketcher.Constraint('PointOnObject', 45, 3, 44))
	constraintList.append(Sketcher.Constraint('PointOnObject', 46, 3, 44))
	constraintList.append(Sketcher.Constraint('Equal', 45, 46))
	constraintList.append(Sketcher.Constraint('Radius', 45, 1.5))
	constraintList.append(Sketcher.Constraint('DistanceX', 45, 3, -1, 1, 35))
	constraintList.append(Sketcher.Constraint('DistanceX', -1, 1, 46, 3, 35))
	
	Boceto_G2D_B.addConstraint(constraintList)
	
	del constraintList
	
	Boceto_G2D_B.renameConstraint(106, u'Radio_03')
	Boceto_G2D_B.setVirtualSpace(106, False)
	Boceto_G2D_B.setExpression('.Constraints.Radio_03', u'Var_001.Radio_Agujero < 1 ? 1 : (Var_001.Radio_Agujero > 5 ? 5 : Var_001.Radio_Agujero)')
	
	Lista_Restr.append([106])
	Lista_Restr[-1].append('Radius   ')
	Lista_Restr[-1].append('45')
	Lista_Restr[-1].append('00')
	Lista_Restr[-1].append('00')
	Lista_Restr[-1].append('00')
	Lista_Restr[-1].append('1.5')
	Lista_Restr[-1].append('Radio_03   ')
	Lista_Restr[-1].append('G_05')
	Lista_Restr[-1].append('NA  ')
	Lista_Restr[-1].append(Boceto_G2D_B.Name)
	
	Doc.recompute()
	
	
	
	# Actualizar_Lista02(LT, AT, RT, Dir_X):
	Lista02 = Actualizar_Lista02(LT, AT, RT, 'V_L')
	
	for k in range(0, len(Lista02)):
		if Lista02[k][0] == 'linea':
			# Crear_Linea(Obj_X, Dir_X, Pt1, Pt2, Boceto_X, Grupo_X = 'G_01', Visible = False):
			Crear_Linea(Lista02[k][0], Lista02[k][1], Lista02[k][2], Lista02[k][3], Boceto_G2D_B, 'G_05', True)
		if Lista02[k][0] == 'circulo':
			# Crear_Circulo(Obj_X, Dir_X, Pt1, Eje, Radio, Boceto_X, Grupo_X = 'G_01', Visible = False):
			Crear_Circulo(Lista02[k][0], Lista02[k][1], Lista02[k][2], Lista02[k][3], Lista02[k][4], Boceto_G2D_B, 'G_05')
	
	del Lista02
	
	constraintList = []
	constraintList.append(Sketcher.Constraint('Coincident', 47, 1, 16, 1))
	constraintList.append(Sketcher.Constraint('Coincident', 47, 2, 8, 1))
	constraintList.append(Sketcher.Constraint('Coincident', 48, 1, 16, 2))
	constraintList.append(Sketcher.Constraint('Coincident', 48, 2, 8, 2))
	constraintList.append(Sketcher.Constraint('Symmetric', 16, 1, 8, 1, 49, 1))
	constraintList.append(Sketcher.Constraint('Symmetric', 16, 2, 8, 2, 49, 2))
	constraintList.append(Sketcher.Constraint('PointOnObject', 50, 3, 49))
	constraintList.append(Sketcher.Constraint('PointOnObject', 51, 3, 49))
	constraintList.append(Sketcher.Constraint('Equal', 50, 51))
	constraintList.append(Sketcher.Constraint('Radius', 50, 1.5))
	constraintList.append(Sketcher.Constraint('DistanceY', -1, 1, 50, 3, 35))
	constraintList.append(Sketcher.Constraint('DistanceY', 51, 3, -1, 1, 35))
	
	Boceto_G2D_B.addConstraint(constraintList)
	
	del constraintList
	
	Boceto_G2D_B.renameConstraint(118, u'Radio_04')
	Boceto_G2D_B.setVirtualSpace(118, False)
	Boceto_G2D_B.setExpression('.Constraints.Radio_04', u'Var_001.Radio_Agujero < 1 ? 1 : (Var_001.Radio_Agujero > 5 ? 5 : Var_001.Radio_Agujero)')
	
	Lista_Restr.append([118])
	Lista_Restr[-1].append('Radius   ')
	Lista_Restr[-1].append('50')
	Lista_Restr[-1].append('00')
	Lista_Restr[-1].append('00')
	Lista_Restr[-1].append('00')
	Lista_Restr[-1].append('1.5')
	Lista_Restr[-1].append('Radio_04   ')
	Lista_Restr[-1].append('G_05')
	Lista_Restr[-1].append('NA  ')
	Lista_Restr[-1].append(Boceto_G2D_B.Name)
	
	Doc.recompute()
	
	
	
	
	
	
	
	
	
	
	
	
	
	
	
	
def Crear_Objeto():
	
	# Limpiar_Pantalla():
	Limpiar_Pantalla()
	
	# Crear_Contenedor():
	Crear_Contenedor()
	
	# Crear_Boceto_Base(Largo_T, Alto_T, Radio_T):
	Crear_Boceto_Base('156 mm', '156 mm', '35 mm')
	
	
	
	
	
	
dias = ('Lun', 'Mar', 'Mie', 'Jue', 'Vie', 'Sab', 'Dom')

Ini = time.time()

#! Inicio de la Macro
Crear_Objeto()



print()
# Imprimir_Lista():
Imprimir_Lista()

	

Fin = time.time()

indice = datetime.date.weekday(datetime.datetime.now())
	
print()

App.Console.PrintMessage(f'Fin de la {Pieza01.Label} en {round(Fin - Ini, 2)} seg\n')

print(f'{dias[indice]}  {time.strftime("%d/%m/%Y  %H:%M:%S", time.localtime())}')


'''
Notas:
	para quitar la seleccion de un objeto
	Gui.Selection.clearSelection()
	
	para seleccionar un objeto
	Gui.Selection.addSelection(App.ActiveDocument.Part_H001)
	
	
'''
