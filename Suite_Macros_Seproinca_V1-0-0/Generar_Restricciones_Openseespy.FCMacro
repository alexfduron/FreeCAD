import FreeCAD as App
import FreeCADGui as Gui
from PySide2 import QtWidgets
import re

# Obtener documento activo
doc = App.ActiveDocument
restricciones = getattr(doc, "Restricciones", None)
if not restricciones:
    raise Exception("No hay restricciones asignadas aún.")

# Paso 1: elegir grados de libertad
tipos_ndf = {
    "2 (X, Y)": 2,
    "3 (X, Y, Z o rotación)": 3,
    "6 (X, Y, Z, Rx, Ry, Rz)": 6
}

tipo, ok = QtWidgets.QInputDialog.getItem(
    None, "Tipo de Modelo",
    "¿Cuántos grados de libertad por nodo (-ndf) tiene tu modelo?",
    list(tipos_ndf.keys()), 0, False
)

if not ok:
    raise Exception("Operación cancelada.")

ndf = tipos_ndf[tipo]

# Paso 2: definir qué grados de libertad restringe cada tipo de apoyo
mapeo = {
    "Empotramiento": [1]*ndf,
    "Articulación Fija": [1 if i < 2 else 0 for i in range(ndf)],  # Fijo en X y Y
    "Rodillo": [0 if i == 0 else 1 for i in range(ndf)],           # Libre en X
    "Libre": [0]*ndf
}

# Buscar nodos y su tipo de restricción
restricciones_por_nodo = []

for obj in restricciones.Group:
    for tipo_str, prefix in [("Empotramiento", "Empotramiento_"),
                             ("Articulación Fija", "ArticulacionFija_"),
                             ("Rodillo", "Rodillo_")]:
        if obj.Name.startswith(prefix):
            nodo_label = obj.Label.replace(prefix, "")
            nodo = doc.getObject(nodo_label)
            if nodo:
                match = re.search(r"(\d+)", nodo.Name)
                if match:
                    numero_nodo = int(match.group(1))
                    restricciones_por_nodo.append((numero_nodo, nodo.Label, mapeo[tipo_str]))
            break

if not restricciones_por_nodo:
    raise Exception("No se encontraron restricciones asignadas.")

# Ordenar por número de nodo
restricciones_por_nodo.sort(key=lambda x: x[0])

# Generar bloque de código numpy
salida = f"# ✅ Bloque de restricciones generado con éxito para modelo con -ndf {ndf}\n\n"

salida += "restricciones = np.array([\n"
for numero, nombre, restricciones in restricciones_por_nodo:
    salida += f"    [{numero}, {', '.join(str(r) for r in restricciones)}],  # Nodo {nombre}\n"
salida += "])\n"

App.Console.PrintMessage(salida + "\n")
