# ================================
# Macro: Ayuda de la Suite de Macros
# Versión: 1.3.2
# Autor: Seproinca
# Compatibilidad: FreeCAD 1.0.0+
# Descripción: Ventana de ayuda con diseño profesional para la suite de macros de Seproinca,
# incluyendo tutoriales gratuitos, soporte y redes sociales.
# Última actualización: 05/08/2025
# ================================

import FreeCAD as App
from PySide2 import QtWidgets, QtGui, QtCore, QtSvg
import webbrowser
import os

class VentanaAyuda(QtWidgets.QDialog):
    def __init__(self):
        super().__init__()
        self.setWindowTitle("Ayuda de la Suite de Macros")
        
         # 🔧 Quitar el botón de ayuda (?) del title bar
        self.setWindowFlag(QtCore.Qt.WindowContextHelpButtonHint, False)
        # (opcional) asegurar que queden título y botón de cerrar
        self.setWindowFlags(self.windowFlags() | QtCore.Qt.WindowTitleHint | QtCore.Qt.WindowCloseButtonHint)


        self.setMinimumWidth(520)  # Solo ancho mínimo, sin altura fija

        # Icono personalizado
        ruta_logo_svg = os.path.join(App.getUserMacroDir(True), "seproinca_logo_vector.svg")
        if os.path.exists(ruta_logo_svg):
            self.setWindowIcon(QtGui.QIcon(ruta_logo_svg))

        # Layout principal
        self.layout = QtWidgets.QVBoxLayout(self)
        self.layout.setContentsMargins(15, 15, 15, 15)  # Márgenes externos
        self.layout.setSpacing(12)  # Espacio vertical entre widgets

        # Logo SVG
        if os.path.exists(ruta_logo_svg):
            logo = QtSvg.QSvgWidget(ruta_logo_svg)
            logo.setFixedSize(100, 100)
            self.layout.addWidget(logo, alignment=QtCore.Qt.AlignCenter)

        # Título
        titulo = QtWidgets.QLabel("<h2>Suite de Macros de Ingeniería Estructural</h2>")
        titulo.setAlignment(QtCore.Qt.AlignCenter)
        self.layout.addWidget(titulo)

        # Mensaje de bienvenida
        bienvenida = QtWidgets.QLabel("<i>Bienvenido a la suite que simplifica tu flujo de trabajo en FreeCAD y OpenSeesPy.</i>")
        bienvenida.setAlignment(QtCore.Qt.AlignCenter)
        bienvenida.setStyleSheet("color: #AAAAAA; margin-bottom: 6px;")
        self.layout.addWidget(bienvenida)

        self._agregar_linea()

        # Descripción
        descripcion = QtWidgets.QLabel("""
        Esta suite automatiza tareas clave en FreeCAD para modelos estructurales:
        • Iniciar la escala visual del modelo.
        • Convertir líneas a miembros.
        • Etiquetar miembros y nodos.
        • Generar el arreglo de nodos y miembros para OpenSeesPy.
        • Asignar vínculos o restricciones externas.
        • Exportar el arreglo de restricciones para OpenSeesPy.
        • Aplicar fuerzas y momentos puntuales.
        • Exportar cargas y momentos en arreglo para OpenSeesPy.
        """)
        descripcion.setWordWrap(True)
        descripcion.setStyleSheet("font-size: 9pt; color: #dddddd;")
        self.layout.addWidget(descripcion)

        # Recuadro de terminología y alcance
        nota_terminologia = QtWidgets.QLabel("""
        <b>Notas importantes:</b><br><br> 
        <i>- Sobre terminología:</i>
        Para mantener compatibilidad con OpenSeesPy, esta suite utiliza:
        • "Nodos" en lugar de “nudos” o “juntas”.
        • "Miembros" en lugar de “elementos”.
        • "Cargas" en lugar de “fuerzas y momentos puntuales”.<br>
        <i>- Sobre alcance:</i> 
        Esta suite está diseñada para agilizar tareas repetitivas de modelado y exportación de datos estructurales,
        reduciendo errores manuales y acelerando el flujo de trabajo con OpenSeesPy.
        No reemplaza el análisis estructural ni el criterio profesional del ingeniero. 
        Los resultados son responsabilidad exclusiva del usuario.
        """)
        nota_terminologia.setWordWrap(True)
        recuadro_terminologia = QtWidgets.QFrame()
        recuadro_terminologia.setStyleSheet("""
            QFrame {
                background-color: #2b2b2b;
                border: 1px solid #444;
                border-radius: 6px;
                padding: 8px;
            }
            QLabel {
                color: #dddddd;
                font-size: 9pt;
            }
        """)
        layout_terminologia = QtWidgets.QVBoxLayout(recuadro_terminologia)
        layout_terminologia.addWidget(nota_terminologia)
        self.layout.addWidget(recuadro_terminologia)

        # Recuadro de Suite Avanzada
        suite_avanzada = QtWidgets.QLabel("""
        <b>Próximamente: Suite Avanzada</b>
        
        🚀 Materiales y Secciones en miembros.
        🚀 Patrones de Carga.
        🚀 Cargas distribuidas en miembros.
        🚀 Ejes Locales.
        🚀 Y mucho más...
        """)
        suite_avanzada.setWordWrap(True)
        recuadro_suite = QtWidgets.QFrame()
        recuadro_suite.setStyleSheet("""
            QFrame {
                background-color: #1f2937;
                border: 1px solid #4b5563;
                border-radius: 6px;
                padding: 8px;
            }
            QLabel {
                color: #cbd5e1;
                font-size: 9pt;
            }
        """)
        layout_suite = QtWidgets.QVBoxLayout(recuadro_suite)
        layout_suite.addWidget(suite_avanzada)
        self.layout.addWidget(recuadro_suite)

        # Autor
        autor = QtWidgets.QLabel("""
        <b>Autoría:</b>
        Desarrollado por <b>Seproinca</b>, empresa dedicada a la formación de ingenieros civiles 
        en proyectos estructurales desde el año <b>2013</b>.
        Síguenos en Instagram: <a href='https://instagram.com/seproinca'>@seproinca</a>
        """)
        autor.setOpenExternalLinks(True)
        autor.setWordWrap(True)
        self.layout.addWidget(autor)

        self._agregar_linea()

        # Botones de acción
        self.botones_widget = QtWidgets.QWidget()
        self.botones_layout = QtWidgets.QHBoxLayout(self.botones_widget)
        self.botones_layout.setSpacing(8)

        self.btn_tutoriales = QtWidgets.QPushButton("📘 Ver tutoriales gratuitos")
        self.btn_instagram = QtWidgets.QPushButton("📲 Seguir en Instagram")
        self.btn_soporte = QtWidgets.QPushButton("🛠 Reportar problemas")

        for btn in (self.btn_tutoriales, self.btn_instagram, self.btn_soporte):
            btn.setStyleSheet("""
                QPushButton {
                    font-weight: bold;
                    padding: 8px;
                    min-width: 160px;
                }
            """)
            self.botones_layout.addWidget(btn)

        self.layout.addWidget(self.botones_widget)

        # Conexiones de botones
        self.btn_tutoriales.clicked.connect(lambda: webbrowser.open("https://aulaseproinca.blogspot.com/search/label/FreeCAD"))
        self.btn_instagram.clicked.connect(lambda: webbrowser.open("https://instagram.com/seproinca"))
        self.btn_soporte.clicked.connect(lambda: webbrowser.open("https://forms.gle/4qsU12eV5DMPZ1BT8"))

        self._agregar_linea()

        # Información de versión
        version = QtWidgets.QLabel("<small>Versión 1.0.0 – Compatible con FreeCAD 1.0.0+</small>")
        version.setAlignment(QtCore.Qt.AlignRight)
        version.setStyleSheet("color: #888888;")
        self.layout.addWidget(version)

        # Botón de cierre
        boton_cerrar = QtWidgets.QDialogButtonBox(QtWidgets.QDialogButtonBox.Close)
        boton_cerrar.rejected.connect(self.reject)
        self.layout.addWidget(boton_cerrar)

        # Ajustar tamaño automáticamente según contenido
        self.adjustSize()
        self.setSizePolicy(QtWidgets.QSizePolicy.Fixed, QtWidgets.QSizePolicy.Fixed)

        self._actualizar_disposicion_botones()

    def _agregar_linea(self):
        linea = QtWidgets.QFrame()
        linea.setFrameShape(QtWidgets.QFrame.HLine)
        linea.setFrameShadow(QtWidgets.QFrame.Sunken)
        self.layout.addWidget(linea)

    def resizeEvent(self, event):
        super().resizeEvent(event)
        self._actualizar_disposicion_botones()

    def _actualizar_disposicion_botones(self):
        ancho = self.width()
        if ancho < 460:
            nuevo_layout = QtWidgets.QVBoxLayout()
        else:
            nuevo_layout = QtWidgets.QHBoxLayout()

        nuevo_layout.setSpacing(8)

        for btn in (self.btn_tutoriales, self.btn_instagram, self.btn_soporte):
            self.botones_layout.removeWidget(btn)
            nuevo_layout.addWidget(btn)

        QtWidgets.QWidget().setLayout(self.botones_layout)
        self.botones_layout = nuevo_layout
        self.botones_widget.setLayout(self.botones_layout)

# Ejecutar ventana
dialog = VentanaAyuda()
dialog.exec_()
